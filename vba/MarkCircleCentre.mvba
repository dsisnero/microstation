Attribute VB_Name = "clsCircleLocator"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
' ---------------------------------------------------------------------
Private Const strMODULE_NAME                As String = "clsCircleLocator"
' ---------------------------------------------------------------------
Implements ILocateCommandEvents
' ---------------------------------------------------------------------

Private Sub ILocateCommandEvents_Accept(ByVal oElement As Element, point As Point3d, ByVal oView As View)
    Dim oEllipse                            As EllipseElement
    If oElement.IsEllipseElement Then
        Set oEllipse = oElement.AsEllipseElement
        Debug.Print "Found ellipse ID " & DLongToString(oEllipse.ID)
        PlaceCentreLines oEllipse
    End If
    
End Sub
' ---------------------------------------------------------------------
Private Sub ILocateCommandEvents_Cleanup()

End Sub
' ---------------------------------------------------------------------
Private Sub ILocateCommandEvents_Dynamics(point As Point3d, ByVal oView As View, ByVal drawMode As MsdDrawingMode)

End Sub
' ---------------------------------------------------------------------
Private Sub ILocateCommandEvents_LocateFailed()

End Sub
' ---------------------------------------------------------------------
Private Sub ILocateCommandEvents_LocateFilter(ByVal oElement As Element, point As Point3d, accepted As Boolean)
    If oElement.IsEllipseElement Then
        accepted = True
    Else
        accepted = False
    End If
End Sub
' ---------------------------------------------------------------------
Private Sub ILocateCommandEvents_LocateReset()

End Sub
' ---------------------------------------------------------------------
Private Sub ILocateCommandEvents_Start()
    Dim oCriteria                           As LocateCriteria
    '  Since this command does  modify the original element,
    '  set the locate criteria to exclude read-only elements.
    Set oCriteria = CommandState.CreateLocateCriteria(True)
    CommandState.SetLocateCriteria oCriteria
    '   The following property was added with MicroStation XM: comment this out for V8.5 or earlier
    '   This adds your command name to MicroStation's state engine, meaning that
    '   the command is visible in the MicroStation's Edit|Undo menu
    CommandState.CommandName = "Mark Circle Centre"
    ShowCommand CommandState.CommandName
    ShowPrompt "Identify ellipse or circle"
End Sub
' ---------------------------------------------------------------------

Attribute VB_Name = "modMain"
Option Explicit
' ---------------------------------------------------------------------
Private Const strMODULE_NAME                As String = "Main"
' ---------------------------------------------------------------------
'   Example code provided by LA Solutions Ltd
'   www.la-solutions.co.uk
' ---------------------------------------------------------------------
'   Notice:
'   This code is provided by LA Solutions Ltd as example code to illustrate
'   aspects of MicroStation VBA programming.  It is provided free of charge
'   with no license obligation or claim of copyright.  It is not warranted
'   fit for any particular purpose: use at your own risk.
'   You may use or reproduce this code for any purpose provided that
'   this notice is retained in full
'   End of notice
' ---------------------------------------------------------------------
'   Updated 16-Jun-2010 LA Solutions Ltd
'   Created 15-Jun-2010 LA Solutions Ltd
' ---------------------------------------------------------------------
'   Type the following in MicroStation's command keyin field to start:
'   vba run [CircleCentreLines]modMain.Main
' ---------------------------------------------------------------------
Public Sub Main()
Attribute Main.VB_Description = "Tool to add lines that denote the centre of a circle or ellipse"
    On Error GoTo err_Main
    CommandState.StartLocate New clsCircleLocator
    Exit Sub
    
err_Main:
    ReportError strMODULE_NAME, "Main"
End Sub
'----------------------------------------------------------------------
'   PlaceCentreLines
'----------------------------------------------------------------------
Public Function PlaceCentreLines(ByVal oEllipse As EllipseElement) As Boolean
    PlaceCentreLines = False
    On Error GoTo err_PlaceCentreLines
    Dim savedGraphicGroup                   As Boolean
    savedGraphicGroup = ActiveSettings.GraphicGroupLockEnabled
    ActiveSettings.GraphicGroupLockEnabled = True
    Dim graphicGroup                        As Long
    graphicGroup = Application.UpdateGraphicGroupNumber
    
    Dim length                              As Double
    length = (oEllipse.PrimaryRadius + oEllipse.SecondaryRadius) / 2#
    length = length + ActiveSettings.TextStyle.Height * 2
    Dim points(0 To 1)                      As Point3d
    '   Four lines that form a cross
    Dim oLine                               As LineElement
    points(0) = oEllipse.CenterPoint
    '   Symbology
    Dim oStyle                              As LineStyle
    Set oStyle = ActiveDesignFile.LineStyles(4)
    Dim colour                              As Long
    colour = oEllipse.Color
    Dim weight                              As Long
    weight = oEllipse.LineWeight
    '   Line 1
    points(1) = oEllipse.CenterPoint
    points(1).X = points(1).X + length
    Set oLine = CreateLineElement1(Nothing, points)
    SetSymbology oLine, oStyle, colour, weight, graphicGroup
    ActiveModelReference.AddElement oLine
    '   Redraw required for V8.5 but not XM or later
    oLine.Redraw msdDrawingModeNormal
    '   Line 2
    points(1) = oEllipse.CenterPoint
    points(1).X = points(1).X - length
    Set oLine = CreateLineElement1(Nothing, points)
    SetSymbology oLine, oStyle, colour, weight, graphicGroup
    ActiveModelReference.AddElement oLine
    '   Redraw required for V8.5 but not XM or later
    oLine.Redraw msdDrawingModeNormal
    '   Line 3
    points(1) = oEllipse.CenterPoint
    points(1).Y = points(1).Y + length
    Set oLine = CreateLineElement1(Nothing, points)
    SetSymbology oLine, oStyle, colour, weight, graphicGroup
    ActiveModelReference.AddElement oLine
    '   Redraw required for V8.5 but not XM or later
    oLine.Redraw msdDrawingModeNormal
    '   Line 4
    points(1) = oEllipse.CenterPoint
    points(1).Y = points(1).Y - length
    Set oLine = CreateLineElement1(Nothing, points)
    SetSymbology oLine, oStyle, colour, weight, graphicGroup
    ActiveModelReference.AddElement oLine
    '   Redraw required for V8.5 but not XM or later
    oLine.Redraw msdDrawingModeNormal
    '   Restore saved graphic group setting
    ActiveSettings.GraphicGroupLockEnabled = savedGraphicGroup
    PlaceCentreLines = True
    Exit Function
    
err_PlaceCentreLines:
    ReportError strMODULE_NAME, "PlaceCentreLines"
End Function
'----------------------------------------------------------------------
'   SetSymbology
'   Apply symbology and graphic group
'----------------------------------------------------------------------
Private Sub SetSymbology(ByRef oElement As Element, ByVal oStyle As LineStyle, ByVal colour As Long, ByVal weight As Long, ByVal graphicGroup As Long)
    On Error GoTo err_SetSymbology
    With oElement
    Set .LineStyle = oStyle
    .Color = colour
    .LineWeight = weight
    .graphicGroup = graphicGroup
    End With
    Exit Sub

err_SetSymbology:
    ReportError strMODULE_NAME, "SetSymbology"
End Sub
'----------------------------------------------------------------------
'   ReportError
'----------------------------------------------------------------------
Public Sub ReportError(ByVal moduleName As String, ByVal procName As String)
    Dim msg As String
    msg = Err.Source & " caused error no. " & CStr(Err.Number) & ":  " & Err.Description
    MsgBox msg, vbOKOnly Or vbCritical, "Error in " & moduleName & ":" & procName
End Sub
