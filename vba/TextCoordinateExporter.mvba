Attribute VB_Name = "clsLevelTools"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
' ---------------------------------------------------------------------
Private Const MODULE_NAME                   As String = "clsLevelTools"
' ---------------------------------------------------------------------
Private Sub NotifyMissingLevel(ByVal levelName As String)
    Dim msg                                 As String
    msg = "Level " & Quote(levelName) & " does not exist in this DGN file"
    ShowMessage msg, msg, msdMessageCenterPriorityWarning, True
    Debug.Print msg
End Sub
' ---------------------------------------------------------------------
'   GetLevel
'   Returns a reference to a named level
' ---------------------------------------------------------------------
Public Function GetLevel(ByVal levelName As String) As Level
    Set GetLevel = Nothing
    If LevelExists(levelName) Then
        Set GetLevel = ActiveModelReference.Levels(levelName)
    End If
    Exit Function
End Function
' ---------------------------------------------------------------------
'   LevelExists
'   Test whether a named level exists.  We provide this function because,
'   if a level does not exist, MicroStation throws an error.  Encapsulating
'   the test lets us hide that error.
'   Returns:    True if the level exists
' ---------------------------------------------------------------------
Public Function LevelExists(ByVal levelName As String) As Boolean
    LevelExists = False
    On Error GoTo err_LevelExists
    Dim nLevels                             As Long
    nLevels = ActiveModelReference.Levels.Count
    Debug.Print "Active model has " & CStr(nLevels) & " levels"
    Dim oLevel                              As Level
    Set oLevel = ActiveModelReference.Levels(levelName)
    If oLevel Is Nothing Then
        '   We never arrive here when MicroStation throws an error
        NotifyMissingLevel levelName
    Else
        LevelExists = True
    End If
    
    Exit Function

err_LevelExists:
    Select Case Err.Number
    Case 5
        '   Expected if level does not exist
        NotifyMissingLevel levelName
    Case Else
        ReportError MODULE_NAME, "LevelExists"
    End Select
End Function
' ---------------------------------------------------------------------

Attribute VB_Name = "clsWord"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
' ---------------------------------------------------------------------
Const MODULE_NAME                           As String = "clsWord"
Const Formatter                             As String = "###0.00"
Const Comma                                 As String = ", "
' ---------------------------------------------------------------------
'   Class Word provides methods to work with a text element
' ---------------------------------------------------------------------
Private m_text                              As String
Private m_origin                            As Point3d
' ---------------------------------------------------------------------
Public Property Let Text(ByVal s As String)
    m_text = s
End Property
Public Property Get Text() As String
    Text = m_text
End Property
' ---------------------------------------------------------------------
Public Property Let Origin(ByRef o As Point3d)
    m_origin = o
End Property
Public Property Get Origin() As Point3d
    Origin = m_origin
End Property
' ---------------------------------------------------------------------
Public Property Set TextElement(ByVal oText As TextElement)
    m_origin = oText.Origin
    m_text = oText.Text
End Property
' ---------------------------------------------------------------------
'   ToCsvLiteral
'   Format the text and origin as comma-separated fields,
' ---------------------------------------------------------------------
Public Property Get ToCsvLiteral() As String
    ToCsvLiteral = m_text & Comma & format(m_origin.X, Formatter) & Comma & format(m_origin.Y, Formatter) & Comma & format(m_origin.Z, Formatter)
End Property
' ---------------------------------------------------------------------
'   ToCsvComputed
'   Format origin as comma-separated fields, taking the Z-value from the text
' ---------------------------------------------------------------------
Public Property Get ToCsvComputed() As String
    ToCsvComputed = format(m_origin.X, Formatter) & Comma & format(m_origin.Y, Formatter) & Comma & format(ExtractValue(m_text), Formatter)
End Property
' ---------------------------------------------------------------------
'   ToString
'   For debug
' ---------------------------------------------------------------------
Public Property Get ToString() As String
    ToString = "'" & m_text & "' XYZ=" & format(m_origin.X, Formatter) & Comma & format(m_origin.Y, Formatter) & Comma & format(m_origin.Z, Formatter)
End Property
' ---------------------------------------------------------------------
Private Function ExtractValue(ByVal s As String) As Double
    ExtractValue = 0
    On Error GoTo err_ExtractValue
    If IsNumeric(s) Then
        ExtractValue = CDbl(s)
    End If
    Exit Function
    
err_ExtractValue:
    ReportError MODULE_NAME, "ExtractValue"
End Function
' ---------------------------------------------------------------------

Attribute VB_Name = "frmExporter"
Attribute VB_Base = "0{7E37E0A0-4DFB-462F-81A9-35A62657E248}{7C339D93-29A4-4D0D-AC8F-E5EAC9ACA09B}"
Attribute VB_GlobalNameSpace = False
Attribute VB_Creatable = False
Attribute VB_PredeclaredId = True
Attribute VB_Exposed = False
Attribute VB_TemplateDerived = False
Attribute VB_Customizable = False
Option Explicit
' ---------------------------------------------------------------------
Private Const MODULE_NAME                   As String = "frmExporter"
' ---------------------------------------------------------------------
Public Enum CsvFormat
    FormatTextXyz = 0
    FormatXyzFromText
End Enum
' ---------------------------------------------------------------------
Private m_nCsvFormat                        As CsvFormat
' ---------------------------------------------------------------------
Private Sub cboFormat_Change()
    Debug.Print "cboFormat " & CStr(cboFormat.ListIndex)
    m_nCsvFormat = cboFormat.ListIndex
End Sub
' ---------------------------------------------------------------------
Private Sub cmdExport_Click()
    Dim oLevelTools                         As New clsLevelTools
    If oLevelTools.LevelExists(txtLevelName.Text) Then
        Dim msg                             As String
        Dim csvFileName                     As String
        csvFileName = "Output.csv"
        Dim initFolder                      As String
        initFolder = txtFolder.Text
        If SaveFile(csvFileName, initFolder, "Export Text Coordinates", "CSV files (*.CSV)", 1) Then
            WriteCoordinates csvFileName, m_nCsvFormat, txtLevelName.Text
        Else
            msg = "User cancelled"
            ShowMessage msg, msg, msdMessageCenterPriorityInfo, False
        End If
    End If
End Sub
' ---------------------------------------------------------------------
Private Sub UserForm_Initialize()
    txtVersion.Text = Version()
    txtFolder.Text = ActiveWorkspace.ConfigurationVariableValue("TEMP")
    cboFormat.AddItem "text, x, y, z"
    cboFormat.AddItem "x, y, z from text"
    cboFormat.ListIndex = FormatTextXyz
End Sub
' ---------------------------------------------------------------------

Attribute VB_Name = "modMain"
Option Explicit
' ---------------------------------------------------------------------
Private Const MODULE_NAME                   As String = "modMain"
Private Const VERSION_                      As String = "18.08.06"
' ---------------------------------------------------------------------
'   Notice
'   This software is provided by LA Solutions Ltd free of copyright.
'   It illustrates certain aspects of VBA programming for MicroStation.
'   You are free to use this software for any purpose provided that
'   this notice is retained in full.
'   Visit our website:
'   www.la-solutions.co.uk
'   End of notice
' ---------------------------------------------------------------------
'   TextCoordinateExporter answers a question asked from time to time
'   on the Be Communities web forums:
'   How do I use an elevation displayed in a text element as a Z value?
'   That is, a text element is placed at a certain X,Y location in 2D
'   so the Z value is zero.  However, the text displayed is the required
'   elevation or Z value.
'   We need to extract the text, at the same timem converting the displayed
'   text to a number and assigning it to the Z value in the text
'   coordinate.
'
'   This code should work in 32-bit VBA6.5 (MicroStation V8i) and
'   64-bit VBA7.1 (MicroStation CONNECT)
' ---------------------------------------------------------------------
'   VBA References
'   This project references the following ActiveX libraries (see menu
'   Tools|References):
'   Windows Scripting Runtime
' ---------------------------------------------------------------------
'   Main entry point
'   MicroStation key-in:
'   vba run [TextCoordinateExporter]modMain.Main
' ---------------------------------------------------------------------
Public Sub Main()
    On Error GoTo err_Main
    Dim msg                                 As String
    msg = "Text Coordinate Exporter by LA Solutions. Version " & Version()
    ShowMessage msg, msg, msdMessageCenterPriorityInfo, False
    
    frmExporter.Show vbModeless
    
    Exit Sub
    
err_Main:
    ReportError MODULE_NAME, "modMain"
End Sub
' ---------------------------------------------------------------------
'   WriteCoordinates
'   Write text coordinates to CSV file
' ---------------------------------------------------------------------
Function WriteCoordinates( _
        ByVal fileName As String, _
        ByVal format As CsvFormat, _
        ByVal levelName As String) As Long
    WriteCoordinates = 0
    On Error GoTo err_WriteCoordinates
    Dim msg                                 As String
    msg = "Save text coordinates to file '" & fileName & "'"
    ShowMessage msg, msg, msdMessageCenterPriorityInfo, False
    Dim oLevelTools                         As New clsLevelTools
    If oLevelTools.LevelExists(levelName) Then
        Dim oFileSystem                     As New Scripting.FileSystemObject
        Dim oFileOut                        As Scripting.TextStream
        Const Overwrite                     As Boolean = True
        Set oFileOut = oFileSystem.CreateTextFile(fileName, Overwrite)
        Dim nTextElements                   As Long
        nTextElements = ScanText(oLevelTools.GetLevel(levelName), oFileOut, format)
        msg = "Saved " & CStr(nTextElements) & " text coordinates  on level '" & levelName & "' to file '" & fileName & "'"
        ShowMessage msg, msg, msdMessageCenterPriorityInfo, False
        Debug.Print msg
        WriteCoordinates = nTextElements
        oFileOut.Close
    End If
    Exit Function
    
err_WriteCoordinates:
    ReportError MODULE_NAME, "WriteCoordinates"
End Function
' ---------------------------------------------------------------------
'   LevelTest
' ---------------------------------------------------------------------
Public Sub LevelTest()
    Const Level1                            As String = "Doesnt Exist"
    Dim oTest                               As New clsLevelTools
    If oTest.LevelExists(Level1) Then
        Debug.Print "Level " & Quote(Level1) & " exists"
    Else
        Debug.Print "Level " & Quote(Level1) & " does not exist"
    End If
    Const Level2                            As String = "Text 2"
    If oTest.LevelExists(Level2) Then
        Debug.Print "Level " & Quote(Level2) & " exists"
    Else
        Debug.Print "Level " & Quote(Level2) & " does not exist"
    End If
    
    Exit Sub

err_LevelTest:
    Debug.Print "Error no. " & CStr(Err.Number)
    ReportError MODULE_NAME, "LevelTest"
End Sub
' ---------------------------------------------------------------------
'   Quote
'   Wrap a string in single quotes
' ---------------------------------------------------------------------
Public Function Quote(ByVal s As String) As String
    Const SingleQuote                       As String = "'"
    Quote = SingleQuote & s & SingleQuote
End Function
' ---------------------------------------------------------------------
'   Version
'   Returns:    Version no. of this project as a String
' ---------------------------------------------------------------------
Public Function Version() As String
    Version = VERSION_
End Function
' ---------------------------------------------------------------------
Sub TraceLevels()
    Dim nLevels As Long
    nLevels = ActiveModelReference.Levels.Count
    Dim n As Long
    For n = 1 To nLevels
        Debug.Print "Level [" & CStr(n) & "] '" & ActiveModelReference.Levels(n).name & "'"
    Next n
End Sub
' ---------------------------------------------------------------------
'   ScanText
'   Scans the active model for text elements on the specified level
'   Returns:    The number of text elements found
' ---------------------------------------------------------------------
Function ScanText(ByVal oLevel As Level, csvFile As Scripting.TextStream, ByVal format As CsvFormat) As Long
    ScanText = 0
    On Error GoTo err_ScanText
    Dim oCriteria                           As New ElementScanCriteria
    oCriteria.ExcludeAllTypes
    oCriteria.IncludeType msdElementTypeText
    oCriteria.ExcludeAllLevels
    oCriteria.IncludeLevel oLevel
    Dim nWords                              As Long
    nWords = 0
    Dim oWords                              As ElementEnumerator
    Set oWords = ActiveModelReference.Scan(oCriteria)
    Do While oWords.MoveNext
        Dim oWord                           As New clsWord
        Set oWord.TextElement = oWords.Current.AsTextElement
        Debug.Print "word: " & oWord.ToString()
        Select Case format
        Case FormatXyzFromText
            csvFile.WriteLine oWord.ToCsvComputed()
        Case FormatTextXyz
            csvFile.WriteLine oWord.ToCsvLiteral()
        End Select
        nWords = 1 + nWords
    Loop
    ScanText = nWords
    Exit Function
    
err_ScanText:
    ReportError MODULE_NAME, "ScanText"
End Function
' ---------------------------------------------------------------------
'   ReportError
'   Generic error-reporting procedure
' ---------------------------------------------------------------------
Public Sub ReportError(ByVal moduleName As String, ByVal procName As String)
    MsgBox "Error no. " & CStr(Err.Number) & " caused by " & Err.Source & vbNewLine & _
        Err.Description, vbExclamation Or vbOKOnly, "Error in " & moduleName & ":" & procName
End Sub
' ---------------------------------------------------------------------

Attribute VB_Name = "modWin32"
Option Explicit
' ---------------------------------------------------------------------
Private Const MODULE_NAME                   As String = "modWin32"
' ---------------------------------------------------------------------
'   Win32 API declarations so that VBA can call
'   Windows functions directly
' ---------------------------------------------------------------------
#If VBA7 Then
    Private Declare PtrSafe Function GetOpenFileName _
        Lib "COMDLG32.DLL" Alias "GetOpenFileNameA" _
        (pOpenfilename As OPENFILENAME) As Long
    Private Declare PtrSafe Function GetSaveFileName _
        Lib "COMDLG32.DLL" Alias "GetSaveFileNameA" _
        (pOpenfilename As OPENFILENAME) As Long

    Private Declare PtrSafe Function SHBrowseForFolder Lib "shell32.dll" _
        Alias "SHBrowseForFolderA" (lpBrowseInfo As BrowseInfo) As Long

    Private Declare PtrSafe Function SHGetPathFromIDList Lib "shell32.dll" _
        (ByVal pidList As LongPtr, ByVal lpBuffer As String) As Long


    Public Declare PtrSafe Function SendMessageA Lib "user32" _
        (ByVal Hwnd As LongPtr, ByVal wMsg As Long, _
        ByVal wParam As LongPtr, lParam As Any) As LongPtr

    Private Declare PtrSafe Sub CoTaskMemFree Lib "ole32.dll" (ByVal hMem As LongPtr)

#Else
    Private Declare Function GetOpenFileName _
        Lib "COMDLG32.DLL" Alias "GetOpenFileNameA" _
        (pOpenfilename As OPENFILENAME) As Long
    Private Declare Function GetSaveFileName _
        Lib "COMDLG32.DLL" Alias "GetSaveFileNameA" _
        (pOpenfilename As OPENFILENAME) As Long
#End If
' ---------------------------------------------------------------------
'   Win32 API structure definition as user-defined type
' ---------------------------------------------------------------------
#If VBA7 Then
    Private Type OPENFILENAME
        lStructSize         As Long
        hWndOwner           As LongPtr
        hInstance           As LongPtr
        lpstrFilter         As String
        lpstrCustomFilter   As String
        nMaxCustFilter      As Long
        nFilterIndex        As Long
        lpstrFile           As String
        nMaxFile            As Long
        lpstrFileTitle      As String
        nMaxFileTitle       As Long
        lpstrInitialDir     As String
        lpstrTitle          As String
        flags               As Long
        nFileOffset         As Integer
        nFileExtension      As Integer
        lpstrDefExt         As String
        lCustData           As Long
        lpfnHook            As LongPtr
        lpTemplateName      As String
    End Type
    
    Public Type BrowseInfo
        hWndOwner           As LongPtr
        pIDLRoot            As LongPtr
        pszDisplayName      As String
        lpszTitle           As String
        ulFlags             As Long
        lpfnCallback        As LongPtr
        lParam              As LongPtr
        iImage              As Long
    End Type
#Else
    Private Type OPENFILENAME
        lStructSize         As Long
        hWndOwner           As Long
        hInstance           As Long
        lpstrFilter         As String
        lpstrCustomFilter   As String
        nMaxCustFilter      As Long
        nFilterIndex        As Long
        lpstrFile           As String
        nMaxFile            As Long
        lpstrFileTitle      As String
        nMaxFileTitle       As Long
        lpstrInitialDir     As String
        lpstrTitle          As String
        flags               As Long
        nFileOffset         As Integer
        nFileExtension      As Integer
        lpstrDefExt         As String
        lCustData           As Long
        lpfnHook            As Long
        lpTemplateName      As String
    End Type
#End If
' ---------------------------------------------------------------------
'   Win32 API constants
' ---------------------------------------------------------------------
Private Const BIF_NEWDIALOGSTYLE            As Long = &H40
Private Const BIF_RETURNONLYFSDIRS          As Long = 1
Private Const MAX_PATH                      As Long = 260
Private Const OFN_OVERWRITEPROMPT           As Long = &H2
Private Const OFN_FILEMUSTEXIST             As Long = &H1000
Private Const OFN_PATHMUSTEXIST             As Long = &H800
Private Const OFN_HIDEREADONLY              As Long = &H4
' ---------------------------------------------------------------------
Function CorrectPath(ByVal sPath As String) As String
    If Right$(sPath, 1) = "\" Then
    If Len(sPath) > 3 Then sPath = Left$(sPath, Len(sPath) - 1) ' Strip backslash from non-root
    Else
    If Len(sPath) = 2 Then sPath = sPath & "\" ' Append backslash to root
    End If
    CorrectPath = sPath
End Function
' ---------------------------------------------------------------------
Private Sub TestOpenFile()
    Dim filter As String
    filter = "*.txt"
    Dim initFolder As String
    initFolder = "L:\Terra Topo"
    Dim title As String
    title = "LA Solutions"
    Dim path As String
    If OpenFile(path, initFolder, title, filter, 1) Then
        Debug.Print "Open file '" & path & "'"
    Else
        Debug.Print "Open file failed"
    End If
End Sub
' ---------------------------------------------------------------------
#If VBA7 Then
    ' -----------------------------------------------------------------
    '   OpenFile
    '   Wraps Win32 function
    '   Returns:    True on success
    ' -----------------------------------------------------------------
    Public Function OpenFile( _
        ByRef strPath As String, _
        ByVal strInitFolder As String, _
        ByVal strTitle As String, _
        ByVal strFilter As String, _
        ByVal nFilterIndex As Long) As Boolean
    
    OpenFile = False
    Dim ofn                                 As OPENFILENAME
    Dim folder                              As String
    folder = CorrectPath(strInitFolder)
    
    ' Swap filter separator for api separator
    Dim filter                              As String
    filter = Replace(strFilter, "|", Chr(0))
    
    With ofn
        .lpstrInitialDir = folder
        .lpstrFilter = filter
        .nFilterIndex = nFilterIndex
        .lpstrTitle = strTitle
    
        .hWndOwner = 0
        .lpstrFile = String(257, 0)
    
        .nMaxFile = LenB(.lpstrFile) - 1
        .lStructSize = LenB(ofn)
    
        .lpstrFileTitle = .lpstrFile
        .nMaxFileTitle = .nMaxFile
    
        .flags = 0
    End With
    
    Dim lReturn                             As Long
    lReturn = GetOpenFileName(ofn)
    If lReturn <> 0 Then
        With ofn
        strPath = Trim(Left(.lpstrFile, InStr(1, .lpstrFile, vbNullChar) - 1))
        End With
        OpenFile = True
    End If

    End Function
    ' -----------------------------------------------------------------
    '   SaveFile
    '   Wraps Win32 function
    '   Returns:    True on success
    ' -----------------------------------------------------------------
    Public Function SaveFile( _
        ByRef strPath As String, _
        ByVal strInitFolder As String, _
        ByVal strTitle As String, _
        ByVal strFilter As String, _
        ByVal nFilterIndex As Long) As Boolean
    
    SaveFile = False
    Dim oFileSystem                         As New Scripting.FileSystemObject
    Dim ofn                                 As OPENFILENAME
    Dim folder                              As String
    folder = CorrectPath(strInitFolder)
    Dim extension                           As String
    extension = oFileSystem.GetExtensionName(strPath)
    ' Swap filter separator for api separator
    Dim filter                              As String
    filter = Replace(strFilter, "|", Chr(0))
    With ofn
        .lpstrInitialDir = folder
        .lpstrFilter = filter
        .nFilterIndex = nFilterIndex
        .lpstrTitle = strTitle
        .lpstrDefExt = extension & vbNullChar
        .hWndOwner = 0
        .lpstrFile = String(257, 0)
    
        .nMaxFile = LenB(.lpstrFile) - 1
        .lStructSize = LenB(ofn)
        '.lpstrFile = strPath
        .lpstrFileTitle = .lpstrFile
        .nMaxFileTitle = .nMaxFile
    
        .flags = 0
    End With
    Dim lReturn                             As Long
    lReturn = GetSaveFileName(ofn)
    If lReturn <> 0 Then
        With ofn
        strPath = Trim(Left(.lpstrFile, InStr(1, .lpstrFile, vbNullChar) - 1))
        Dim ext2                            As String
        ext2 = oFileSystem.GetExtensionName(strPath)
        If vbNullString = ext2 Or 0 <> StrComp(ext2, extension) Then
            strPath = strPath & "." & extension
        End If
        End With
        SaveFile = True
    End If
    Set oFileSystem = Nothing

End Function
#Else
    ' -----------------------------------------------------------------
    '   OpenFile
    '   Wraps Win32 function
    '   Returns:    True on success
    ' -----------------------------------------------------------------
    Public Function OpenFile(ByRef path As String, ByVal title As String) As Boolean
        OpenFile = False
        Dim ofn                                 As OPENFILENAME
        With ofn
            .lStructSize = Len(ofn)     ' Size of structure.
            .nMaxFile = 260             ' Size of buffer.
            ' Create buffer.
            .lpstrFile = String(.nMaxFile - 1, 0)
            .lpstrTitle = title
            Dim ret                             As Long
            ret = GetOpenFileName(ofn)  ' Call function.
            If ret <> 0 Then            ' Non-zero is success.
                ' Find first null char.
                Dim firstNull                   As Integer
                firstNull = InStr(.lpstrFile, vbNullChar)
                path = Left(.lpstrFile, firstNull - 1)
                OpenFile = True
            End If
        End With
    End Function
    ' -----------------------------------------------------------------
    '   SaveFile
    '   Wraps Win32 function
    '   Returns:    True on success
    ' -----------------------------------------------------------------
    Public Function SaveFile( _
        ByRef strPath As String, _
        ByVal strInitFolder As String, _
        ByVal strTitle As String, _
        ByVal strFilter As String, _
        ByVal nFilterIndex As Long) As Boolean
    
    SaveFile = False
    Dim oFileSystem                         As New Scripting.FileSystemObject
    Dim ofn                                 As OPENFILENAME
    Dim folder                              As String
    folder = CorrectPath(strInitFolder)
    Dim extension                           As String
    extension = oFileSystem.GetExtensionName(strPath)
    ' Swap filter separator for api separator
    Dim filter                              As String
    filter = Replace(strFilter, "|", Chr(0))
    With ofn
        .lpstrInitialDir = folder
        .lpstrFilter = filter
        .nFilterIndex = nFilterIndex
        .lpstrTitle = strTitle
        .lpstrDefExt = extension & vbNullChar
        .hWndOwner = 0
        .lpstrFile = String(257, 0)
    
        .nMaxFile = LenB(.lpstrFile) - 1
        .lStructSize = LenB(ofn)
        '.lpstrFile = strPath
        .lpstrFileTitle = .lpstrFile
        .nMaxFileTitle = .nMaxFile
    
        .flags = 0
    End With
    Dim lReturn                             As Long
    lReturn = GetSaveFileName(ofn)
    If lReturn <> 0 Then
        With ofn
        strPath = Trim(Left(.lpstrFile, InStr(1, .lpstrFile, vbNullChar) - 1))
        Dim ext2                            As String
        ext2 = oFileSystem.GetExtensionName(strPath)
        If vbNullString = ext2 Or 0 <> StrComp(ext2, extension) Then
            strPath = strPath & "." & extension
        End If
        End With
        SaveFile = True
    End If
    Set oFileSystem = Nothing

    End Function
#End If
' ---------------------------------------------------------------------
'   Test procedure
' ---------------------------------------------------------------------
Private Sub TestGetFileFromAPI()
  Dim ofn As OPENFILENAME
  With ofn
    .lStructSize = LenB(ofn)     ' Size of structure.
    .nMaxFile = 260             ' Size of buffer.
    ' Create buffer.
    .lpstrFile = String(.nMaxFile - 1, 0)
    Dim ret As Long
    Dim n As Integer
    ret = GetOpenFileName(ofn)  ' Call function.
    If ret <> 0 Then            ' Non-zero is success.
      ' Find first null char.
      n = InStr(.lpstrFile, vbNullChar)
      ' Return what's before it.
      MsgBox Left(.lpstrFile, n - 1)
    End If
  End With
End Sub
' ---------------------------------------------------------------------
