Attribute VB_Name = "clsCellPlaceAndDrop"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
' ---------------------------------------------------------------------
'   Cell Placer class
' ---------------------------------------------------------------------
Implements IPrimitiveCommandEvents
' ---------------------------------------------------------------------
Private Const MODULE_NAME                   As String = "clsCellPlaceAndDrop"
' ---------------------------------------------------------------------
'   Cell place-and-drop class
' ---------------------------------------------------------------------
Private m_strCellName As String
' ---------------------------------------------------------------------
Public Property Let CellName(ByVal name As String)
    m_strCellName = name
End Property
Public Property Get CellName() As String
    CellName = m_strCellName
End Property
' ---------------------------------------------------------------------
Private Sub IPrimitiveCommandEvents_Cleanup()

End Sub
' ---------------------------------------------------------------------
'   DropCell
'   Drop cell to its components and add them to active model
' ---------------------------------------------------------------------
Private Sub DropCell(ByVal oCell As CellElement)
    Dim oComponents As ElementEnumerator
    Set oComponents = oCell.Drop
    Do While oComponents.MoveNext
        Dim oElement As Element
        Set oElement = oComponents.Current
        ActiveModelReference.AddElement oElement
    Loop
End Sub
' ---------------------------------------------------------------------
Private Sub CreateCell(ByRef point As Point3d, ByVal drawMode As MsdDrawingMode)
    Dim oCell As CellElement
    Set oCell = CreateCellElement2(m_strCellName, point, Point3dOne, True, Matrix3dIdentity)
    If drawMode = msdDrawingModeNormal Then
        'ActiveModelReference.AddElement oCell
        DropCell oCell
    Else
        oCell.Redraw drawMode
    End If
End Sub
' ---------------------------------------------------------------------
Private Sub IPrimitiveCommandEvents_DataPoint(point As Point3d, ByVal View As View)
    CreateCell point, msdDrawingModeNormal
End Sub
' ---------------------------------------------------------------------
Private Sub IPrimitiveCommandEvents_Dynamics(point As Point3d, ByVal View As View, ByVal drawMode As MsdDrawingMode)
    CreateCell point, drawMode
End Sub
' ---------------------------------------------------------------------
Private Sub IPrimitiveCommandEvents_Keyin(ByVal keyin As String)
    m_strCellName = keyin
End Sub
' ---------------------------------------------------------------------
Private Sub IPrimitiveCommandEvents_Reset()

End Sub
' ---------------------------------------------------------------------
Private Sub IPrimitiveCommandEvents_Start()
    CommandState.CommandName = "Cell Place and Drop Example"
    ShowCommand CommandState.CommandName
    ShowPrompt "Place cell"
    CommandState.StartDynamics
End Sub
' ---------------------------------------------------------------------

Attribute VB_Name = "clsCellPlacer"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
' ---------------------------------------------------------------------
Private Const MODULE_NAME                   As String = "clsCellPlacer"
' ---------------------------------------------------------------------
'   Cell Placer class
' ---------------------------------------------------------------------
Implements IPrimitiveCommandEvents
' ---------------------------------------------------------------------
Private m_strCellName As String
' ---------------------------------------------------------------------
Public Property Let CellName(ByVal name As String)
    m_strCellName = name
End Property
Public Property Get CellName() As String
    CellName = m_strCellName
End Property
' ---------------------------------------------------------------------
Private Sub IPrimitiveCommandEvents_Cleanup()

End Sub
' ---------------------------------------------------------------------
Private Sub CreateCell(ByRef point As Point3d, ByVal drawMode As MsdDrawingMode)
    Dim oCell As CellElement
    Set oCell = CreateCellElement2(m_strCellName, point, Point3dOne, True, Matrix3dIdentity)
    If drawMode = msdDrawingModeNormal Then
        ActiveModelReference.AddElement oCell
    Else
        oCell.Redraw drawMode
    End If
End Sub
' ---------------------------------------------------------------------
Private Sub IPrimitiveCommandEvents_DataPoint(point As Point3d, ByVal View As View)
    CreateCell point, msdDrawingModeNormal
End Sub
' ---------------------------------------------------------------------
Private Sub IPrimitiveCommandEvents_Dynamics(point As Point3d, ByVal View As View, ByVal drawMode As MsdDrawingMode)
    CreateCell point, drawMode
End Sub
' ---------------------------------------------------------------------
Private Sub IPrimitiveCommandEvents_Keyin(ByVal keyin As String)
    m_strCellName = keyin
End Sub
' ---------------------------------------------------------------------
Private Sub IPrimitiveCommandEvents_Reset()

End Sub
' ---------------------------------------------------------------------
Private Sub IPrimitiveCommandEvents_Start()
    CommandState.CommandName = "Cell Placement Example"
    ShowCommand CommandState.CommandName
    ShowPrompt "Place cell"
    CommandState.StartDynamics
End Sub
' ---------------------------------------------------------------------

Attribute VB_Name = "modMain"
Option Explicit
' ---------------------------------------------------------------------
Private Const MODULE_NAME                   As String = "modMain"
' ---------------------------------------------------------------------
'   Notice:
'   LA Solutions Ltd
'   This sample MicroStation VBA code is provided free of charge as-is
'   to illustrate program logic.  You may use this code for whatever
'   purpose private or commercial provided that this notice is retained
'   in full.
'   www.la-solutions.co.uk
'   End of notice
' ---------------------------------------------------------------------
'   MicroStation key-in:
'   vba run [CellPlacement]modMain.PlaceCell
' ---------------------------------------------------------------------
Public Sub PlaceCell()
    Dim oCellPlacer As New clsCellPlacer
    oCellPlacer.CellName = ActiveSettings.CellName
    Const WantKeyins  As Boolean = True
    CommandState.StartPrimitive oCellPlacer, WantKeyins
End Sub
' ---------------------------------------------------------------------
'   MicroStation key-in:
'   vba run [CellPlacement]modMain.PlaceAndDropCell
' ---------------------------------------------------------------------
Public Sub PlaceAndDropCell()
    Dim oCellPlacer As New clsCellPlaceAndDrop
    oCellPlacer.CellName = ActiveSettings.CellName
    Const WantKeyins  As Boolean = True
    CommandState.StartPrimitive oCellPlacer, WantKeyins
End Sub
' ---------------------------------------------------------------------
