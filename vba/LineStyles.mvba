Attribute VB_Name = "clsLineStyleList"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
' ---------------------------------------------------------------------
Private Const MODULE_NAME                   As String = "clsLineStyleList"
' ---------------------------------------------------------------------
'   Class Line Style List wraps MDL functions to get line style names
' ---------------------------------------------------------------------
Private m_styleStringList                   As Long '   Pointer to MDL StringList
Private m_nSource                           As LineStyleSourceOptions
Private m_nWidthStringList                  As Long '   N columns in MDL StringList
' ---------------------------------------------------------------------
'   MDL function declarations
' ---------------------------------------------------------------------
Private Declare Function mdlLineStyle_nameGetStringList Lib "stdmdlbltin.dll" ( _
        ByVal pAuxInfo As Long, _
        ByVal options As Long) As Long    ' Returns void *
Private Declare Function mdlStringList_destroy Lib "stdmdlbltin.dll" ( _
        ByVal list As Long) As Long ' Returns SUCCESS
Private Declare Function mdlStringList_size Lib "stdmdlbltin.dll" (ByVal list As Long) As Long  '  Returns N members
Private Declare Function mdlStringList_getMember Lib "stdmdlbltin.dll" ( _
        ByRef pString As Long, _
        ByRef pInfo As Long, _
        ByVal list As Long, _
        ByVal n As Long) As Long ' Returns SUCCESS
Private Declare Function mdlLineStyle_getLinNames Lib "stdmdlbltin.dll" ( _
        ByVal linFileName As String, _
        ByVal numInfoFields As Long) As Long  ' Returns void *
' ---------------------------------------------------------------------
'   Win32 function declarations
' ---------------------------------------------------------------------
Private Declare Function SysAllocString Lib "oleaut32" (ByVal charPtr As Long) As String
' ---------------------------------------------------------------------
'   See mslstyle.h for #defines
'   #define LSSL_OPT_RSCONLY    0x01
'   #define LSSL_OPT_MASTONLY   0x02
' ---------------------------------------------------------------------
Public Enum LineStyleSourceOptions
    OptionAll = 0
    OptionDgnLib = 1
    OptionLocal = 2
    OptionRsc = 3
End Enum
' ---------------------------------------------------------------------
'   DescribeSource
'   Describe the source where the current set of line styles was obtained
'   Returns:    String description
' ---------------------------------------------------------------------
Public Property Get DescribeSource() As String
    Select Case m_nSource
    Case OptionAll
        DescribeSource = " line styles from all sources"
    Case OptionDgnLib
        DescribeSource = " line styles in DGNLibs"
    Case OptionLocal
        DescribeSource = " line styles in active DGN file"
    Case OptionRsc
        DescribeSource = " line styles in resource file"
    End Select
End Property
' ---------------------------------------------------------------------
'   StyleExists
'   Test to find if the named line style exists in the current list
'   Returns:    True if style is matched
' ---------------------------------------------------------------------
Public Function StyleExists(ByVal candidate As String) As Boolean
    StyleExists = False
    On Error GoTo err_StyleExists
    
    If 0 < LineStyleCount Then
        Dim n                               As Long
        For n = 0 To LineStyleCount - 1
            Dim name                        As String
            name = LineStyleByIndex(n)
            If 0 = StrComp(candidate, name, vbTextCompare) Then
                StyleExists = True
                Exit Function
            End If
        Next n
    End If
    Exit Function
    
err_StyleExists:
    ReportError MODULE_NAME, "StyleExists"
End Function
' ---------------------------------------------------------------------
'   GetResourceLineStyles
'   Get a list of line style names from a resource (*.lin) file.
'   This is a 2-column string list with names and descriptions
' ---------------------------------------------------------------------
Public Sub GetResourceLineStyles(ByVal fileName As String)
    m_nSource = OptionRsc
    m_nWidthStringList = 2
    m_styleStringList = mdlLineStyle_getLinNames(fileName, 0)
End Sub
' ---------------------------------------------------------------------
Public Sub GetActiveDgnLineStyles()
    StringListDestroy m_styleStringList
    m_nSource = OptionLocal
    m_styleStringList = GetStringList(m_nSource)
End Sub
' ---------------------------------------------------------------------
Public Sub GetDgnLibLineStyles()
    StringListDestroy m_styleStringList
    m_nSource = OptionDgnLib
    m_styleStringList = GetStringList(m_nSource)
End Sub
' ---------------------------------------------------------------------
Public Sub GetAllLineStyles()
    StringListDestroy m_styleStringList
    m_nSource = OptionAll
    m_styleStringList = GetStringList(m_nSource)
End Sub
' ---------------------------------------------------------------------
Private Function GetStringList(ByVal source As Long) As Long
    m_nWidthStringList = 1
    GetStringList = mdlLineStyle_nameGetStringList(0, source)
End Function
' ---------------------------------------------------------------------
Public Property Get CountLineStylesInActiveDGN() As Long
     GetActiveDgnLineStyles
     CountLineStylesInActiveDGN = LineStyleCount
End Property
' ---------------------------------------------------------------------
Public Property Get CountLineStylesInDGNLibs() As Long
    GetDgnLibLineStyles
    CountLineStylesInDGNLibs = LineStyleCount
End Property
' ---------------------------------------------------------------------
'  Creates a VBA String from a C char *
' ---------------------------------------------------------------------
Private Function CharPtrToString(charPtr As Long) As String
    If charPtr = 0 Then
        CharPtrToString = vbNullString
    Else
        CharPtrToString = SysAllocString(charPtr)
    End If
End Function
' ---------------------------------------------------------------------
'   LineStyleCount
'   Return the number of line styles in our list
' ---------------------------------------------------------------------
Public Property Get LineStyleCount() As Long
    LineStyleCount = StringListSize() / m_nWidthStringList
End Property
' ---------------------------------------------------------------------
Private Function StringListSize() As Long
    Dim rc                                  As Long
    rc = mdlStringList_size(m_styleStringList)
    If rc = -1 Then
        '   Invalid pointer
        StringListSize = 0
    Else
        StringListSize = rc
    End If
End Function
' ---------------------------------------------------------------------
'   TraceStyleNames
'   Print each line style name to the VBA immediate window
' ---------------------------------------------------------------------
Public Sub TraceStyleNames()
    Dim nMembers                            As Long
    nMembers = LineStyleCount
    Dim msg                                 As String
    msg = "There are " & CStr(nMembers) & DescribeSource
    Debug.Print msg
    Dim n                                   As Long
    For n = 0 To nMembers - 1
        Dim s                               As String
        s = LineStyleByIndex(n)
        msg = "Line Style [" & CStr(n + 1) & "] " & SingleQuote(s)
        Debug.Print msg
    Next n
End Sub
' ---------------------------------------------------------------------
'   StringListDestroy
'   Free memory allocated by MDL
' ---------------------------------------------------------------------
Private Sub StringListDestroy(ByRef list As Long)
    If 0 <> list Then
        mdlStringList_destroy list
        list = 0
    End If
End Sub
' ---------------------------------------------------------------------
'   LineStyleByIndex
'   Get the Nth style in a list, allowing for the width of the StringList
'   Valid indices are 0..LineStyleCount - 1
' ---------------------------------------------------------------------
Public Function LineStyleByIndex(ByVal n As Long) As String
    LineStyleByIndex = vbNullString
    Debug.Assert 0 <= n And n < LineStyleCount
    LineStyleByIndex = StringListGetMember(n * m_nWidthStringList)
End Function
' ---------------------------------------------------------------------
'   StringListGetMember
'   Get the Nth member of a StringList
' ---------------------------------------------------------------------
Private Function StringListGetMember(ByVal n As Long) As String
    StringListGetMember = vbNullString
    On Error GoTo err_StringListGetMember
    Debug.Assert 0 <= n And n < StringListSize()
    Dim s                                   As String
    Dim pString                             As Long
    pString = 0
    '  _getMember puts the address of a char* into pString,
    mdlStringList_getMember pString, 0, m_styleStringList, n
    '   pString now points at a C string buffer
    s = CharPtrToString(pString)
    '   Find where the C string is terminated (with a NULL)
    Dim nullPosition                        As Long
    nullPosition = InStr(1, s, vbNullChar)
    If nullPosition > 0 Then s = Left$(s, InStr(1, s, vbNullChar) - 1)
    'Debug.Print SingleQuote(s)
    StringListGetMember = s
    Exit Function
    
err_StringListGetMember:
    ReportError MODULE_NAME, "StringListGetMember"
End Function
' ---------------------------------------------------------------------
Private Sub Class_Initialize()
    m_styleStringList = 0
    m_nWidthStringList = 1
End Sub
' ---------------------------------------------------------------------
'   Class destructor
' ---------------------------------------------------------------------
Private Sub Class_Terminate()
    StringListDestroy m_styleStringList
End Sub
' ---------------------------------------------------------------------

Attribute VB_Name = "modMain"
Option Explicit
' ---------------------------------------------------------------------
Private Const MODULE_NAME                   As String = "modMain"
Private Const VERSION_                      As String = "16.8.27.1"
' ---------------------------------------------------------------------
'   Line style tests
' ---------------------------------------------------------------------
'   Notice:
'   This code is provided to illustrate MicroStation VBA programming.
'   This example shows how to obtain MicroStation line style names
'   from either the active DGN file or from DGNLibs.  Since VBA
'   can't distinguish the source of a line style, we resort to
'   MDL functions.  We wrap those functions inside a VBA class,
'   which makes it simple to use.
'   It is not guaranteed fit for any particular purpose.  Use at your
'   own risk.

'   You may use this software for any purpose commercial or private
'   provided that this notice is retained in full.
'   www.la-solutions.co.uk
'   End of Notice
' ---------------------------------------------------------------------
'   Entry point for interactive use.
'   Key-in:
'   vba run [LineStyles]modMain.Main
' ---------------------------------------------------------------------
Public Sub Main()
    On Error GoTo err_Main
    Dim msg                                 As String
    msg = "[LineStyles]modMain.Main version " & Version()
    Debug.Print msg
    ShowMessage msg, msg, msdMessageCenterPriorityInfo, False
    
    'TraceLineStyles
    
    Dim oLineStyles                         As New clsLineStyleList
    oLineStyles.GetDgnLibLineStyles
    oLineStyles.TraceStyleNames
    Dim count                               As Long
    count = oLineStyles.CountLineStylesInActiveDGN
    Debug.Print "There are " & CStr(count) & " line styles in the active DGN file"
    count = oLineStyles.CountLineStylesInDGNLibs
    Debug.Print "There are " & CStr(count) & " line styles in DGNLibs"
    
    Dim folder                              As String
    If GetLineStyleDir(folder) Then
        Debug.Print "MS_LINFILELIST=" & SingleQuote(folder)
        Dim fileName                        As String
        Const FileTitle                     As String = "plotstyles.lin"
        fileName = folder & FileTitle
        oLineStyles.GetResourceLineStyles (fileName)
        Debug.Print "Line styles from " & SingleQuote(FileTitle)
        oLineStyles.TraceStyleNames
        Const Test                          As String = "ACAD_ISO09W100"
        If oLineStyles.StyleExists(Test) Then
            Debug.Print "Line Style " & SingleQuote(Test) & " exists"
        Else
            Debug.Print "Line Style " & SingleQuote(Test) & " does not exist"
        End If
        Const Test2                         As String = "LA Solutions"
        If oLineStyles.StyleExists(Test2) Then
            Debug.Print "Line Style " & SingleQuote(Test2) & " exists"
        Else
            Debug.Print "Line Style " & SingleQuote(Test2) & " does not exist"
        End If
    End If
    
    Set oLineStyles = Nothing
    Exit Sub
    
err_Main:
    ReportError MODULE_NAME, "Main"
End Sub
' ---------------------------------------------------------------------
Private Sub TestGetMsDataDir()
    Dim folder                              As String
    If GetLineStyleDir(folder) Then
        Debug.Print "MS_LINFILELIST=" & SingleQuote(folder)
    Else
        Debug.Print "MS_LINFILELIST is not defined"
    End If
End Sub
' ---------------------------------------------------------------------
'   GetMsDataDir
'   Get the folder specified in MS_LINFILELIST
'   Returns:    True if the configuration variable is defined
' ---------------------------------------------------------------------
Public Function GetLineStyleDir(ByRef folder As String) As Boolean
    GetLineStyleDir = False
    On Error GoTo err_GetMsDataDir
    Const CfgVar                            As String = "MS_LINFILELIST"
    If ActiveWorkspace.IsConfigurationVariableDefined(CfgVar) Then
        GetLineStyleDir = True
        folder = ActiveWorkspace.ConfigurationVariableValue(CfgVar)
    End If
    Exit Function
    
err_GetMsDataDir:
    ReportError MODULE_NAME, "GetLineStyleDir"
End Function
' ---------------------------------------------------------------------
'   TraceLineStyles
'   Print a list of line styles visible from VBA.  Note that VBA tells
'   you what line styles are available from both the active DGN file
'   and from DGNLibs.  It can't distinguish between those sources.
' ---------------------------------------------------------------------
Sub TraceLineStyles()
    On Error GoTo err_TraceLineStyles
    Dim oStyles                             As LineStyles
    Set oStyles = ActiveDesignFile.LineStyles
    Dim oStyle                              As LineStyle
    For Each oStyle In oStyles
        Debug.Print "Line style " & SingleQuote(oStyle.name)
    Next oStyle
    Exit Sub
    
err_TraceLineStyles:
    ReportError MODULE_NAME, "TraceLineStyles"
End Sub
' ---------------------------------------------------------------------
Public Function Version() As String
    Version = VERSION_
End Function
' ---------------------------------------------------------------------
'   DoubleQuote
'   Wrap a string in double quote marks
' ---------------------------------------------------------------------
Public Function DoubleQuote(ByVal s As String) As String
    Const Quote                             As String = """"
    DoubleQuote = Quote & s & Quote
End Function
' ---------------------------------------------------------------------
'   SingleQuote
'   Wrap a string in single quote marks
' ---------------------------------------------------------------------
Public Function SingleQuote(ByVal s As String) As String
    Const Quote                             As String = "'"
    SingleQuote = Quote & s & Quote
End Function
' ---------------------------------------------------------------------
'   ReportError
'   Report errors in a consistent manner
' ---------------------------------------------------------------------
Public Sub ReportError(ByVal moduleName As String, ByVal procName As String)
    MsgBox "Error no. " & CStr(Err.Number) & ": " & Err.Description & vbNewLine & "Caused by " & Err.source, vbOKOnly Or vbExclamation, "Error in " & moduleName & ":" & procName
End Sub
' ---------------------------------------------------------------------
