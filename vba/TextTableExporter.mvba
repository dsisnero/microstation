Attribute VB_Name = "clsFencePlacementTool"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
' ---------------------------------------------------------------------
Private Const MODULE_NAME                   As String = "clsFencePlacementTool"
' ---------------------------------------------------------------------
Implements IPrimitiveCommandEvents
' ---------------------------------------------------------------------
Private m_points(0 To 1)                    As Point3d
Private m_nPoints                           As Long
' ---------------------------------------------------------------------
Private Sub IPrimitiveCommandEvents_Cleanup()
    m_nPoints = 0
    CommandState.StopDynamics
End Sub
' ---------------------------------------------------------------------
Private Sub DrawRectangle( _
        ByVal DrawMode As MsdDrawingMode, _
        ByVal createFence As Boolean, _
        ByVal oView As View)
    On Error GoTo err_DrawRectangle
    Dim vertices(0 To 4)                    As Point3d
    Dim v                                   As Long
    For v = 0 To 4
        vertices(v) = m_points(0)
    Next v
    vertices(1).X = m_points(1).X
    vertices(2).X = m_points(1).X
    vertices(2).Y = m_points(1).Y
    vertices(3).Y = m_points(1).Y
    Dim oShape                              As ShapeElement
    Set oShape = CreateShapeElement1(Nothing, vertices, msdFillModeNotFilled)
    oShape.Redraw DrawMode
    If createFence Then
        Dim oFence                          As Fence
        Set oFence = ActiveDesignFile.Fence
        oFence.DefineFromElement oView, oShape
    oFence.Draw

    End If
    Exit Sub
    
err_DrawRectangle:
    ReportError MODULE_NAME, "DrawRectangle"
End Sub
' ---------------------------------------------------------------------
Private Sub IPrimitiveCommandEvents_DataPoint(Point As Point3d, ByVal oView As View)
    m_points(m_nPoints) = Point
    m_nPoints = 1 + m_nPoints
    CommandState.StartDynamics
    If 1 = m_nPoints Then ShowPrompt "Place opposite corner of fence"
    If 2 = m_nPoints Then
        
        DrawRectangle msdDrawingModeNormal, True, oView
        AnalyseFenceContents
    End If
End Sub
' ---------------------------------------------------------------------
Private Sub IPrimitiveCommandEvents_Dynamics(Point As Point3d, ByVal oView As View, ByVal DrawMode As MsdDrawingMode)
    m_points(m_nPoints) = Point
    DrawRectangle DrawMode, False, oView
End Sub
' ---------------------------------------------------------------------
Private Sub IPrimitiveCommandEvents_Keyin(ByVal Keyin As String)

End Sub
' ---------------------------------------------------------------------
Private Sub IPrimitiveCommandEvents_Reset()

End Sub
' ---------------------------------------------------------------------
Private Sub IPrimitiveCommandEvents_Start()
    CommandState.CommandName = "Export Table Text"
    ShowCommand CommandState.CommandName
    ShowPrompt "Place first fence point"
    m_nPoints = 0
End Sub
' ---------------------------------------------------------------------

Attribute VB_Name = "frmTextTableExport"
Attribute VB_Base = "0{F4676967-01F4-4358-975A-CF8F832FCF3B}{FDF50041-7273-4869-B0B5-0F9ED550549E}"
Attribute VB_GlobalNameSpace = False
Attribute VB_Creatable = False
Attribute VB_PredeclaredId = True
Attribute VB_Exposed = False
Attribute VB_TemplateDerived = False
Attribute VB_Customizable = False
Option Explicit
' ---------------------------------------------------------------------
Private Const MODULE_NAME                   As String = "frmTextTableExport"
' ---------------------------------------------------------------------
Private m_oTextStream                       As Scripting.TextStream
' ---------------------------------------------------------------------
Public Property Get CsvFile() As Scripting.TextStream
    Set CsvFile = m_oTextStream
End Property
' ---------------------------------------------------------------------
Private Sub cmdBrowse_Click()

End Sub
' ---------------------------------------------------------------------
Private Sub cmdExport_Click()
    If OpenCsvFile(m_oTextStream, txtFileName.text) Then
        CommandState.StartPrimitive New clsFencePlacementTool
    Else
        Dim msg                             As String
        msg = "Unable to open file '" & txtFileName.text & "' for writing"
        ShowMessage msg, msg, msdMessageCenterPriorityError, True
    End If
End Sub
' ---------------------------------------------------------------------
Private Sub UserForm_Initialize()
    txtVersion.text = "Version " & Version()
    Dim tempDir                             As String
    '   Get the Windows temporary folder (e.g. C:\TEMP)
    tempDir = ActiveWorkspace.ConfigurationVariableValue("TEMP")
    txtFileName.text = tempDir & "\" & ReplaceExtension(ActiveDesignFile.Name, "csv")
End Sub
' ---------------------------------------------------------------------

Attribute VB_Name = "modMain"
Option Explicit
' ---------------------------------------------------------------------
Private Const MODULE_NAME                   As String = "modMain"
Public Const VERSION_                       As String = "19.07.30.0"
Public Const APP_NAME                       As String = "Text Table Exporter"
#If Win64 Then
Private Const WELCOME_MESSAGE               As String = "Welcome to LA Solutions' " & _
                                                        APP_NAME & " version " & VERSION_ & _
                                                        " for MicroStation CONNECT"
#Else
Private Const WELCOME_MESSAGE               As String = "Welcome to LA Solutions' " & _
                                                        APP_NAME & " version " & VERSION_ & _
                                                        " for MicroStation V8i"
#End If
' ---------------------------------------------------------------------
'   Notice:
'   This MicroStation VBA macro is designed to collect text elements
'   from a 'table'.  It sorts the text elements using spatial analysis.
'   Finally, it writes the contents of the text elements as a CSV file.
'
'   This code is written to demonstrate MicroStation VBA coding.  It is
'   not fit for any particular purpose.  Use at your own risk.
'
'   You may use this code for any purpose provided that this notice is
'   retained in full.
'
'   Visit our website:
'   http://www.la-solutions.co.uk
'
'   End of notice
' ---------------------------------------------------------------------
'   VBA References:
'   This project references the Scripting Runtime library
' ---------------------------------------------------------------------
Public Function Version() As String
    Version = VERSION_
End Function
' ---------------------------------------------------------------------
Public Function AppName() As String
    AppName = APP_NAME
End Function
' ---------------------------------------------------------------------
'   Main
'   Main entry point
'   key-in:
'   vba run [TextTableExporter]modMain.Main
' ---------------------------------------------------------------------
Public Sub Main()
    On Error GoTo err_Main
    Dim msg                                 As String
    msg = WELCOME_MESSAGE
    ShowMessage msg, AppName() & " version " & Version() & " created by LA Solutions Ltd", msdMessageCenterPriorityInfo, False
    ActiveDesignFile.Fence.Undefine
    frmTextTableExport.Show vbModeless
    Exit Sub
    
err_Main:
    ReportError MODULE_NAME, "Main"
End Sub
' ---------------------------------------------------------------------
'   OpenCsvFile
'   Open the specified file as a Scripting.TextStream
' ---------------------------------------------------------------------
Public Function OpenCsvFile( _
        ByRef oTextStream As Scripting.TextStream, _
        ByVal fileName As String) As Boolean
    OpenCsvFile = False
    On Error GoTo err_OpenCsvFile
    Dim oFileSystem                         As New Scripting.FileSystemObject
    Const Overwrite                         As Boolean = True
    Set oTextStream = oFileSystem.CreateTextFile(fileName, Overwrite)
    Set oFileSystem = Nothing
    OpenCsvFile = True
    Exit Function
    
err_OpenCsvFile:
    ReportError MODULE_NAME, "OpenCsvFile"
End Function
' ---------------------------------------------------------------------
'   AnalyseFenceContents
'   Get text elements contained within the fence.  We return here once
'   the Place Fence tool has completed
' ---------------------------------------------------------------------
Public Sub AnalyseFenceContents()
    On Error GoTo err_AnalyseFenceContents
    Dim msg                                 As String
    Dim oFence                              As Fence
    Set oFence = ActiveDesignFile.Fence
    If oFence.IsDefined Then
        Dim oContents                       As ElementEnumerator
        Set oContents = oFence.GetContents
        '   Assign text into rows and columns
        Dim grid()                          As Element
        grid = oContents.BuildArrayFromContents
        Dim words()                         As TextElement
        words = FilterTextElements(grid)
        Dim word                            As Long
        For word = LBound(words) To UBound(words)
            Debug.Print "Word [" & CStr(word) & "]=" & words(word).text
        Next word
        Dim corners(2)                      As Range3d
        FindCorners corners, words
        Dim textWidth                       As Double
        textWidth = words(1).TextStyle.width
        Dim origin                          As Point3d
        origin = corners(1).High
        Dim column1()                       As TextElement
        column1 = FindFirstColumn(origin, textWidth, words)
        Dim nRows                           As Long
        nRows = AnalyseRows(column1, words, frmTextTableExport.CsvFile)
        Select Case nRows
        Case 0
            msg = "No rows written to CSV file"
            ShowMessage msg, msg, msdMessageCenterPriorityWarning, False
        Case 1
            msg = "Wrote one table row to CSV file"
            ShowMessage msg, msg, msdMessageCenterPriorityInfo, False
        Case Else
            msg = "Wrote " & CStr(nRows) & " table rows to CSV file"
            ShowMessage msg, msg, msdMessageCenterPriorityInfo, False
        End Select
    Else
        msg = "No fence is defined"
        ShowMessage msg, msg, msdMessageCenterPriorityWarning, True
    End If
    CommandState.StartDefaultCommand
    Exit Sub
    
err_AnalyseFenceContents:
    ReportError MODULE_NAME, "AnalyseFenceContents"
End Sub
' ---------------------------------------------------------------------
'   CalculateTextHeight
'   If the Text Style is valid, get its height.  Otherwise, calculate the
'   height from the range of the passed text element.
'   Returns:    Double text height
' ---------------------------------------------------------------------
Private Function CalculateTextHeight(ByVal oText As TextElement) As Double
    If oText.TextStyle Is Nothing Or vbNullString = oText.TextStyle.Name Then
        Dim width                           As Double
        Dim height                          As Double
        oText.GetTextTileSize width, height
        '   This is guesstimation
        'height = 2 * height / ActiveModelReference.UORsPerMasterUnit
        height = 1.2 * height / ActiveModelReference.UORsPerMasterUnit
        Debug.Print "Calculated Text tile height=" & CStr(height)
        CalculateTextHeight = height
    Else
        CalculateTextHeight = oText.TextStyle.height
    End If
End Function
' ---------------------------------------------------------------------
'   AnalyseRows
'   Column1() is a sorted list of the TextElements in the first column.
'   For each member of Column1(), find TextElements in the same row
'   and put them into a sorted array.
' ---------------------------------------------------------------------
Private Function AnalyseRows( _
        ByRef column1() As TextElement, _
        ByRef words() As TextElement, _
        ByVal oTextStream As Scripting.TextStream) As Long
    On Error GoTo err_AnalyseRows
    AnalyseRows = 0
    Dim textHeight                          As Double
    Debug.Print "words(1).TextStyle '" & words(1).TextStyle.Name & "'"
    textHeight = CalculateTextHeight(words(1))
    Dim nRows                               As Long
    nRows = UBound(column1) - LBound(column1) + 1
    Debug.Print "N Rows=" & CStr(nRows)
    Dim row                                 As Long
    For row = 0 To nRows - 1
        Debug.Print "Analysing row [" & CStr(row) & "] " & column1(row).text
        Dim origin                          As Point3d
        origin = column1(row).origin
        Dim columns()                       As TextElement
        GetColumnsInRow columns, words, origin, textHeight, row
        WriteRowData columns, oTextStream
        origin = column1(row).origin
    Next row
    oTextStream.Close
    AnalyseRows = nRows
    Exit Function
    
err_AnalyseRows:
    ReportError MODULE_NAME, "AnalyseRows"
End Function
' ---------------------------------------------------------------------
'   WriteRowData
'   Write each column as a comma-separated-variable
' ---------------------------------------------------------------------
Private Function WriteRowData(ByRef columns() As TextElement, ByVal oTextStream As Scripting.TextStream) As Boolean
    WriteRowData = False
    On Error GoTo err_WriteRowData
    Const Separator                         As String = ","
    Dim line                                As String
    Dim nCols                               As Long
    nCols = UBound(columns) - LBound(columns) + 1
    Dim text                                As String
    Dim col                                 As Long
    For col = 0 To nCols - 1
        text = columns(col).text
        If 0 < InStr(text, Separator) Then
            text = DoubleQuote(text)
        End If
        
        If 0 = col Then
            line = line & text
        Else
            line = line & Separator & text
        End If
    Next col
    oTextStream.WriteLine line
    Exit Function
    
err_WriteRowData:
    ReportError MODULE_NAME, "WriteRowData"
End Function
' ---------------------------------------------------------------------
'   ReplaceExtension
'   Provide a file name e.g. file.dgn and a new extension e.g. csv, and
'   this function returns file.csv
' ---------------------------------------------------------------------
Public Function ReplaceExtension(ByVal fileName As String, ByVal newExtension As String) As String
    Dim oFileSystem                         As New Scripting.FileSystemObject
    Const Dot                               As String = "."
    Dim extension                           As String
    extension = Dot & oFileSystem.GetExtensionName(fileName)
    ReplaceExtension = Replace(fileName, extension, Dot & newExtension)
    Set oFileSystem = Nothing
End Function
' ---------------------------------------------------------------------
'   DoubleQuote
'   Wrap string in double quotes
' ---------------------------------------------------------------------
Public Function DoubleQuote(ByVal s As String) As String
    Const Quote                             As String = """"
    DoubleQuote = Quote & s & Quote
End Function
' ---------------------------------------------------------------------
'   Quote
'   Wrap string in single quotes
' ---------------------------------------------------------------------
Public Function Quote(ByVal s As String) As String
    Const SingleQuote                       As String = "'"
    Quote = SingleQuote & s & SingleQuote
End Function
' ---------------------------------------------------------------------
'   GetColumnsInRow
'   Fill an array of TextElement with words on the same horizontal as
'   origin within tolerance TextHeight
'   Returns:    Long column count
' ---------------------------------------------------------------------
Private Function GetColumnsInRow( _
        ByRef columns() As TextElement, _
        ByRef words() As TextElement, _
        ByRef origin As Point3d, _
        ByVal textHeight As Double, _
        ByVal rowNum As Long) As Long
    GetColumnsInRow = 0
    On Error GoTo err_GetColumnsInRow
    ReDim columns(0)
    Dim col                                 As Long
    Dim nColumns                            As Long
    nColumns = 0
    Dim word                                As Long
    Dim nWords                              As Long
    nWords = UBound(words) - LBound(words) + 1
    For word = 1 To nWords
        If IsSameRow(origin, words(word).origin, textHeight) Then
            nColumns = 1 + nColumns
            ReDim Preserve columns(0 To nColumns - 1)
            Set columns(nColumns - 1) = words(word)
        End If
    Next word
    SortHorizontal columns, origin, True
    Debug.Print "Row no. " & CStr(rowNum)
    For col = 0 To nColumns - 1
        Debug.Print "[" & CStr(col) & "] " & columns(col).text
    Next col
    Exit Function
    
err_GetColumnsInRow:
    ReportError MODULE_NAME, "GetColumnsInRow"
End Function
' ---------------------------------------------------------------------
'   SortVertical
'   Sort an array of TextElement by Y value
' ---------------------------------------------------------------------
Private Sub SortVertical(ByRef col() As TextElement, ByRef origin As Point3d, ByVal ascending As Boolean)
    On Error GoTo err_SortVertical
    'Debug.Print "SortVertical nRows=" & CStr(UBound(col) - LBound(col) + 1) & _
    '    " origin " & FormatPoint3dXY(origin)
    Dim oTemp                               As TextElement
    Dim row                                 As Long
    'For row = LBound(col) To UBound(col)
    '    Debug.Print FormatDouble(col(row).origin.Y)
    'Next row
    '   Sort an array using bubble sort algorithm
    Dim first                               As Long, _
        last                                As Long
    Dim i                                   As Long, _
        j                                   As Long
    
    first = LBound(col)
    last = UBound(col)
    For i = first To last - 1
        For j = i + 1 To last
            If (col(i).origin.Y < col(j).origin.Y) Xor ascending Then
                Set oTemp = col(j)
                Set col(j) = col(i)
                Set col(i) = oTemp
            End If
        Next j
    Next i
    'Debug.Print "Sorted..."
    'For row = LBound(col) To UBound(col)
    '    Debug.Print FormatDouble(col(row).origin.Y)
    'Next row
    Exit Sub
    
err_SortVertical:
    ReportError MODULE_NAME, "SortVertical"
End Sub
' ---------------------------------------------------------------------
'   SortHorizontal
'   Sort an array of TextElement by X value
' ---------------------------------------------------------------------
Private Sub SortHorizontal(ByRef row() As TextElement, ByRef origin As Point3d, ByVal ascending As Boolean)
    On Error GoTo err_SortHorizontal
    Debug.Print "SortHorizontal nCols=" & CStr(UBound(row) - LBound(row) + 1) & _
        " origin " & FormatPoint3dXY(origin)
    Dim oTemp                               As TextElement
    Dim col                                 As Long
    'For col = LBound(row) To UBound(row)
    '    Debug.Print FormatDouble(row(col).origin.X)
    'Next col
    '   Sort an array using bubble sort algorithm
    Dim first                               As Long, _
        last                                As Long
    Dim i                                   As Long, _
        j                                   As Long
    
    first = LBound(row)
    last = UBound(row)
    For i = first To last - 1
        For j = i + 1 To last
            If (row(i).origin.X < row(j).origin.X) Xor ascending Then
                Set oTemp = row(j)
                Set row(j) = row(i)
                Set row(i) = oTemp
            End If
        Next j
    Next i
    'Debug.Print "Sorted..."
    'For col = LBound(row) To UBound(row)
    '    Debug.Print FormatDouble(row(col).origin.X)
    'Next col
    Exit Sub
    
err_SortHorizontal:
    ReportError MODULE_NAME, "SortHorizontal"
End Sub
' ---------------------------------------------------------------------
'   FindFirstColumn
'   Find the first text element in each row
'   Returns:    TextElement list sorted by vertical position
' ---------------------------------------------------------------------
Private Function FindFirstColumn(ByRef origin As Point3d, ByVal textWidth As Double, ByRef words() As TextElement) As TextElement()
    On Error GoTo err_FindFirstColumn
    Dim col()                               As TextElement
    Dim nRows                               As Long
    nRows = 0
    Dim word                                As Long
    For word = LBound(words) To UBound(words)
        If IsSameColumn(origin, words(word).origin, textWidth) Then
            nRows = 1 + nRows
            ReDim Preserve col(0 To nRows - 1)
            Set col(nRows - 1) = words(word)
        End If
    Next word
    Const DecreasingY                       As Boolean = False
    SortVertical col, origin, DecreasingY
    FindFirstColumn = col
    Debug.Print "FindFirstColumn nRows=" & CStr(nRows)
    Dim row                                 As Long
    For row = 0 To nRows - 1
        Debug.Print "Row [" & CStr(row) & "] text '" & col(row).text & "'"
    Next row
    Exit Function
    
err_FindFirstColumn:
    ReportError MODULE_NAME, "FindFirstColumn"
End Function
' ---------------------------------------------------------------------
'   Find the next row below the current row starting at origin.
'   Returns:    Point3d start of next row
' ---------------------------------------------------------------------
Private Function GetStartOfNextRow(ByRef origin As Point3d, ByVal textHeight As Double, ByRef words() As TextElement) As Point3d
    Dim nextRow                             As Point3d
    nextRow = origin
    nextRow.Y = nextRow.Y - textHeight
    GetStartOfNextRow = nextRow
End Function
' ---------------------------------------------------------------------
'   IsSameColumn
'   Test whether a text element is within TextWidth of a reference point.
'   Returns:    True if within tolerance.
' ---------------------------------------------------------------------
Private Function IsSameColumn(ByRef origin As Point3d, ByRef textOrigin As Point3d, ByVal textWidth As Double) As Boolean
    IsSameColumn = textWidth > Abs(origin.X - textOrigin.X)
End Function
' ---------------------------------------------------------------------
'   IsSameRow
'   Test whether a text element is within TextHeight of a reference point.
'   Returns:    True if within tolerance.
' ---------------------------------------------------------------------
Private Function IsSameRow(ByRef origin As Point3d, ByRef textOrigin As Point3d, ByVal textHeight As Double) As Boolean
    IsSameRow = textHeight > Abs(origin.Y - textOrigin.Y)
End Function
' ---------------------------------------------------------------------
'   FindTextInRow
'   Find text elements on the same horizontal as origin
' ---------------------------------------------------------------------
Private Function FindTextInRow(ByRef origin As Point3d, ByVal textHeight As Double, ByRef words() As TextElement) As Long
    On Error GoTo err_FindTextInRow
    Dim nColumns                            As Long
    nColumns = 0
    Dim row()                               As TextElement
    Dim word                                As Long
    For word = LBound(words) To UBound(words)
        If IsSameRow(origin, words(word).origin, textHeight) Then
            nColumns = 1 + nColumns
            ReDim Preserve row(0 To nColumns - 1)
            Set row(nColumns - 1) = words(word)
        End If
    Next word
    Debug.Print "nColumns=" & CStr(nColumns)
    Dim col                                 As Long
    For col = 0 To nColumns - 1
        Debug.Print "Column [" & CStr(col) & "] text '" & row(col).text & "'"
    Next col
    FindTextInRow = nColumns
    Exit Function
    
err_FindTextInRow:
    ReportError MODULE_NAME, "FindTextInRow"
End Function
' ---------------------------------------------------------------------
'   FindCorners
'   Examine the array of TextElement to find the top-left, top-right,
'   bottom-left and bottom-right corners
' ---------------------------------------------------------------------
Private Sub FindCorners(ByRef corners() As Range3d, ByRef words() As TextElement)
    '   Top left and bottom right corners
    Dim topLeft                             As Range3d
    topLeft = Range3dInit
    '   Top right and bottom left corners
    Dim topRight                            As Range3d
    topRight = Range3dInit
    
    '   Initialise ranges to first word location
    topLeft.High = words(1).origin
    topLeft.Low = words(1).origin
    topRight.High = words(1).origin
    topRight.Low = words(1).origin
    Dim word                                As Long
    For word = LBound(words) To UBound(words)
        Debug.Print "Word [" & CStr(word) & "]=" & words(word).text
        '   X extents
        With words(word).origin
        topLeft.High.X = IIf(.X < topLeft.High.X, .X, topLeft.High.X)
        topLeft.Low.X = IIf(.X > topLeft.Low.X, .X, topLeft.Low.X)
        topRight.High.X = IIf(.X > topRight.High.X, .X, topRight.High.X)
        topRight.Low.X = IIf(.X < topRight.Low.X, .X, topRight.Low.X)
        '   Y extents
        topLeft.High.Y = IIf(.Y > topLeft.High.Y, .Y, topLeft.High.Y)
        topRight.High.Y = IIf(.Y > topRight.High.Y, .Y, topRight.High.Y)
        topLeft.Low.Y = IIf(.Y < topLeft.Low.Y, .Y, topLeft.Low.Y)
        'topRight.Low.Y = IIf(.Y < topLeft.Low.Y, .Y, topLeft.Low.Y)
        topRight.Low.Y = IIf(.Y < topRight.Low.Y, .Y, topRight.Low.Y)
        End With
    Next word
    corners(1) = topLeft
    corners(2) = topRight
    Debug.Print "Top left=" & FormatPoint3dXY(corners(1).High)
    Debug.Print "Top right=" & FormatPoint3dXY(corners(2).High)
    Debug.Print "Bottom left=" & FormatPoint3dXY(corners(2).Low)
    Debug.Print "Bottom right=" & FormatPoint3dXY(corners(1).Low)
End Sub
' ---------------------------------------------------------------------
'   ExtractText
'   Extract a text element from either existing text or a component
'   of a Text node.
'   Returns:    True if extracted successfully
' ---------------------------------------------------------------------
Private Function ExtractText(ByRef oExtract As TextElement, ByVal oElement As Element) As Boolean
    ExtractText = False
    On Error GoTo err_ExtractText
    Select Case oElement.Type
    Case msdElementTypeText
        Set oExtract = oElement.AsTextElement
        ExtractText = True
    Case msdElementTypeTextNode
        Dim oWords                          As ElementEnumerator
        Set oWords = oElement.AsTextNodeElement.GetSubElements
        '   Copy the first text element
        oWords.MoveNext
        Set oExtract = oWords.Current.AsTextElement.Clone
        ExtractText = True
    End Select
    Exit Function
    
err_ExtractText:
    ReportError MODULE_NAME, "ExtractText"
End Function
' ---------------------------------------------------------------------
'   FilterTextElements
'   Returns an array of TextElement
' ---------------------------------------------------------------------
Private Function FilterTextElements(ByRef grid() As Element) As TextElement()
    On Error GoTo err_FilterTextElements
    Debug.Print "FilterTextElements"
    Dim nFound                              As Long
    nFound = 0
    Dim nWords                              As Long
    nWords = UBound(grid) - LBound(grid) + 1
    Debug.Print "nWords=" & CStr(nWords)
    Dim word                                As Long
    For word = 0 To nWords - 1
        If grid(word).IsTextElement Or grid(word).IsTextNodeElement Then
            nFound = 1 + nFound
        End If
    Next word
    Debug.Print "nFound=" & CStr(nFound)
    Dim words()                             As TextElement
    ReDim words(1 To nFound)
    nFound = 0
    For word = 0 To nWords - 1
        Dim oExtract                        As TextElement
        If ExtractText(oExtract, grid(word)) Then
            nFound = 1 + nFound
            'Debug.Print "copy '" & oExtract.text & "'"
            Set words(nFound) = oExtract
        End If
    Next word
    
    FilterTextElements = words
    Exit Function
    
err_FilterTextElements:
    ReportError MODULE_NAME, "FilterTextElements"
End Function
' ---------------------------------------------------------------------
'   FormatDouble
'   Create a String with a formatted double number
' ---------------------------------------------------------------------
Function FormatDouble(ByVal val As Double) As String
    FormatDouble = Format(val, "##0.00")
End Function
' ---------------------------------------------------------------------
'   FormatPoint3dXY
'   Format the XY components of a Point3d into a string
' ---------------------------------------------------------------------
Function FormatPoint3dXY(ByRef p As Point3d) As String
    FormatPoint3dXY = FormatDouble(p.X) & "," & FormatDouble(p.Y)
End Function
' ---------------------------------------------------------------------
'   ProcessWord
'   Process text found in fence
' ---------------------------------------------------------------------
Sub ProcessWord(ByVal oWord As TextElement)
    On Error GoTo err_ProcessWord
    Debug.Print "Process text '" & oWord.text & "'"
    Exit Sub
    
err_ProcessWord:
    ReportError MODULE_NAME, "ProcessWord"
End Sub
' ---------------------------------------------------------------------
'   ReportError
'   Provides consistent error reporting
' ---------------------------------------------------------------------
Public Sub ReportError(ByVal moduleName As String, ByVal procName As String)
    MsgBox "Error " & CStr(Err.Number) & " was caused by " & vbNewLine & _
        Err.Source & ". " & vbNewLine & _
        Err.Description, vbOKOnly Or vbExclamation, "Error in " & moduleName & ":" & procName
End Sub
' ---------------------------------------------------------------------
