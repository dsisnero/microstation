Attribute VB_Name = "clsInteractiveMarker"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
' ---------------------------------------------------------------------
Private Const MODULE_NAME                   As String = "clsInteractiveMarker"
' ---------------------------------------------------------------------
'   clsInteractiveMarker
'   A class that implements IPrimitiveCommandEvents to show a marker
'   dynamically 'linked' to a linear element.
'   The _Dynamics event creates a text element at the hit point of a
'   perpendicular drawn from the current cursor position onto the linear element.
'   The text is rotated to the tangent of the linear element at the hit point.
' ---------------------------------------------------------------------
'   The linear element can be a line, line-string, complex string, curve,
'   arc or B-spline element.
Private m_oLinearElement               As Element
' ---------------------------------------------------------------------
Implements IPrimitiveCommandEvents
' ---------------------------------------------------------------------
Public Property Set LinearElement(ByVal oElement As Element)
    Set m_oLinearElement = oElement
End Property
' ---------------------------------------------------------------------
Private Sub IPrimitiveCommandEvents_Cleanup()

End Sub
' ---------------------------------------------------------------------
Private Sub IPrimitiveCommandEvents_DataPoint(point As Point3d, ByVal oView As View)

End Sub
' ---------------------------------------------------------------------
'   GetHitPoint
'   Project a perpendicular from the cursor location to our element.
'   Returns the projected point.
' ---------------------------------------------------------------------
Private Function GetHitPoint(ByRef cursor As Point3d, ByVal oView As View) As Point3d
    Dim viewRotation                        As Matrix3d
    viewRotation = oView.rotation
    Select Case m_oLinearElement.Type
    Case msdElementTypeLine, msdElementTypeLineString
        GetHitPoint = m_oLinearElement.AsLineElement.ProjectPointOnPerpendicular(cursor, viewRotation)
    Case msdElementTypeCurve
        GetHitPoint = m_oLinearElement.AsCurveElement.ProjectPointOnPerpendicular(cursor, viewRotation)
    Case msdElementTypeArc
        GetHitPoint = m_oLinearElement.AsArcElement.ProjectPointOnPerpendicular(cursor, viewRotation)
    Case msdElementTypeBsplineCurve
        GetHitPoint = m_oLinearElement.AsBsplineCurveElement.ProjectPointOnPerpendicular(cursor, viewRotation)
    Case msdElementTypeComplexString
        GetHitPoint = m_oLinearElement.AsComplexStringElement.ProjectPointOnPerpendicular(cursor, viewRotation)
    End Select
End Function
' ---------------------------------------------------------------------
'   CalculateRotationAtHitPoint
'   Calculate the angle of the perpendicular at the hit point on the
'   linear element.
' ---------------------------------------------------------------------
Private Function CalculateRotationAtHitPoint(ByRef pt1 As Point3d, ByRef pt2 As Point3d, ByVal oView As View) As Matrix3d
    Const Z                                 As Long = 2
    Dim perpendicular                       As Vector3d
    perpendicular = Vector3dFromPoint3d(Point3dSubtract(pt1, pt2))
    Dim radians                             As Double
    radians = Vector3dAngleBetweenVectorsXY( _
                perpendicular, _
                Vector3dFromXYZ(1, 0, 0))
    CalculateRotationAtHitPoint = Matrix3dInverse(Matrix3dFromAxisAndRotationAngle(Z, radians))
End Function
' ---------------------------------------------------------------------
'   CalculatTangentRotationAtHitPoint
'   Rotate the perpendicular rotation by Pi/2 radians about the Z axis
' ---------------------------------------------------------------------
Private Function CalculatTangentRotationAtHitPoint(hitPoint As Point3d, perpendicular As Matrix3d, oView As View) As Matrix3d
    Const Z                                 As Long = 2
    Dim rotateByPiOver2                     As Matrix3d
    rotateByPiOver2 = Matrix3dFromAxisAndRotationAngle(Z, Pi / 2)
    CalculatTangentRotationAtHitPoint = Matrix3dFromMatrix3dTimesMatrix3d(rotateByPiOver2, perpendicular)
End Function
' ---------------------------------------------------------------------
Private Sub IPrimitiveCommandEvents_Dynamics(cursor As Point3d, ByVal oView As View, ByVal drawMode As MsdDrawingMode)
    Dim hitPoint                            As Point3d
    hitPoint = GetHitPoint(cursor, oView)
    Dim rotation                            As Matrix3d
    rotation = CalculateRotationAtHitPoint(cursor, hitPoint, oView)
    Dim tangent                             As Matrix3d
    tangent = CalculatTangentRotationAtHitPoint(hitPoint, rotation, oView)
    Dim oText                               As TextElement
    'Set oText = CreateTextElement1(Nothing, "Follow Line", hitPoint, tangent)
    Set oText = CreateTextElement1(Nothing, "Follow Line", hitPoint, rotation)
    oText.Redraw drawMode
    Dim oSleeper                            As CellElement
    Set oSleeper = CreateCellElement2(MARKER_CELL_NAME, hitPoint, Point3dOne, True, tangent)
    oSleeper.Redraw drawMode
End Sub
' ---------------------------------------------------------------------
Private Sub IPrimitiveCommandEvents_Keyin(ByVal Keyin As String)

End Sub
' ---------------------------------------------------------------------
Private Sub IPrimitiveCommandEvents_Reset()

End Sub
' ---------------------------------------------------------------------
Private Sub IPrimitiveCommandEvents_Start()
    If m_oLinearElement Is Nothing Then
        Dim msg                             As String
        msg = "Set LinearElement before starting this class"
        ShowMessage msg, msg, msdMessageCenterPriorityWarning, True
        Exit Sub
    End If
    
    ShowCommand "Follow Line Example"
    ShowPrompt "Place mark near line"
    CommandState.StartDynamics
End Sub
' ---------------------------------------------------------------------

Attribute VB_Name = "clsLinePicker"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
' ---------------------------------------------------------------------
Private Const MODULE_NAME                   As String = "clsLinePicker"
' ---------------------------------------------------------------------
Implements ILocateCommandEvents
' ---------------------------------------------------------------------
Private m_bInteractive                      As Boolean
Private m_dblSpacing                        As Double
' ---------------------------------------------------------------------
Public Property Let Interactive(ByVal i As Boolean)
    m_bInteractive = i
End Property
' ---------------------------------------------------------------------
Public Property Get Spacing() As Double
    Spacing = m_dblSpacing
End Property
' ---------------------------------------------------------------------
Public Property Let Spacing(ByVal d As Double)
    If (0# < d) Then
        m_dblSpacing = d
    Else
        Dim msg                             As String
        msg = MODULE_NAME & ": Spacing.  Value must be a positive number."
        ShowMessage msg, msg, msdMessageCenterPriorityError, True
    End If
End Property
' ---------------------------------------------------------------------
Private Sub ILocateCommandEvents_Accept(ByVal oElement As Element, point As Point3d, ByVal View As View)
    If m_bInteractive Then
        Dim oMarker                             As New clsInteractiveMarker
        Set oMarker.LinearElement = oElement
        CommandState.StartPrimitive oMarker
    Else
        CommandState.CommandName = "Place markers along element"
        Dim oLinearMarker                       As New clsLinearMarker
        Set oLinearMarker.LinearElement = oElement
        oLinearMarker.Spacing = m_dblSpacing
        Dim nMarkers                        As Long
        nMarkers = oLinearMarker.CreateMarkers()
        Dim msg                                 As String
        msg = "Created " & CStr(nMarkers) & " on linear element"
        ShowMessage msg, msg, msdMessageCenterPriorityInfo
        CommandState.StartDefaultCommand
    End If
End Sub
' ---------------------------------------------------------------------
Private Sub ILocateCommandEvents_Cleanup()

End Sub
' ---------------------------------------------------------------------
'   Dynamics is called only if you have previously initiated dynamics
'   using CommandState.StartDynamics
' ---------------------------------------------------------------------
Private Sub ILocateCommandEvents_Dynamics(point As Point3d, ByVal oView As View, ByVal drawMode As MsdDrawingMode)
    Dim oText                               As TextElement
    Set oText = CreateTextElement1(Nothing, "Follow Line", point, Matrix3dIdentity)
    oText.Redraw drawMode
End Sub
' ---------------------------------------------------------------------
Private Sub ILocateCommandEvents_LocateFailed()

End Sub
' ---------------------------------------------------------------------
Private Sub ILocateCommandEvents_LocateFilter(ByVal oElement As Element, point As Point3d, accepted As Boolean)
    accepted = oElement.IsTraversableElement
End Sub
' ---------------------------------------------------------------------
Private Sub ILocateCommandEvents_LocateReset()

End Sub
' ---------------------------------------------------------------------
Private Sub ILocateCommandEvents_Start()
    Dim oLocateCriteria                     As LocateCriteria

    '  Since this command does not modify the original element,
    '  set the locate criteria to allow  read-only elements.
    Set oLocateCriteria = CommandState.CreateLocateCriteria(False)
    CommandState.SetLocateCriteria oLocateCriteria

    ShowCommand "Follow Line Example"
    ShowPrompt "Select a line, line-string or arc"
End Sub
' ---------------------------------------------------------------------

Attribute VB_Name = "clsLinearMarker"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
' ---------------------------------------------------------------------
Private Const MODULE_NAME                   As String = "clsLinearMarker"
' ---------------------------------------------------------------------
'   clsLinearMarker
'   A class that draws a set of marker elements, such as a cell,
'   along a linear element.
'   The marker is rotated to the tangent to the linear element at each point.
' ---------------------------------------------------------------------
'   The linear element can be a line, line-string, complex string, curve,
'   arc or B-spline element.
Private m_oLinearElement                As Element
Private m_oSpline                       As BsplineCurve
Private m_dblSpacing                    As Double
' ---------------------------------------------------------------------
Public Property Set LinearElement(ByVal oElement As Element)
    Set m_oLinearElement = oElement
    Set m_oSpline = New BsplineCurve
    m_oSpline.FromElement oElement
    Debug.Assert Not m_oSpline Is Nothing
End Property
' ---------------------------------------------------------------------
Public Property Let Spacing(ByVal d As Double)
    If (0# < d) Then
        m_dblSpacing = d
    Else
        Dim msg                             As String
        msg = MODULE_NAME & ": Spacing.  Value must be a positive number."
        ShowMessage msg, msg, msdMessageCenterPriorityError, True
    End If
End Property
' ---------------------------------------------------------------------
'   CreateMarkers
'   Create markers along our linear element every Separation units.
'   Returns: Count of markers placed.
' ---------------------------------------------------------------------
Public Function CreateMarkers() As Long
    CreateMarkers = 0
    On Error GoTo err_CreateMarkers
    Dim msg                                 As String
    If m_oLinearElement Is Nothing Then
        msg = MODULE_NAME & ": CreateMarkers.  You must set LinearElement before calling this method."
        ShowMessage msg, msg, msdMessageCenterPriorityError, True
        Exit Function
    End If
    
    If 0 >= m_dblSpacing Then
        msg = MODULE_NAME & ": CreateMarkers.  You must set Spacing before calling this method."
        ShowMessage msg, msg, msdMessageCenterPriorityError, True
        Exit Function
    End If
    Const Z                                 As Long = 2
    Dim length                              As Double
    length = m_oSpline.ComputeCurveLength()
    Dim nMarkers                            As Long
    nMarkers = length / m_dblSpacing
    msg = "About to place " & CStr(nMarkers) & " markers"
    ShowMessage msg, msg, msdMessageCenterPriorityInfo
    Dim param                               As Double
    Dim n                                   As Long
    For n = 1 To nMarkers
        Dim current                         As Point3d
        Dim tangent                         As Point3d
        current = m_oSpline.EvaluatePointAtDistance(param, n * m_dblSpacing)
        m_oSpline.EvaluatePointTangent tangent, param
        Dim radians                         As Double
        radians = Vector3dAngleBetweenVectorsXY( _
                    Vector3dFromPoint3d(tangent), _
                    Vector3dFromXYZ(1, 0, 0))
        Dim rotation                        As Matrix3d
        rotation = Matrix3dInverse(Matrix3dFromAxisAndRotationAngle(Z, radians))
        Dim oCell                           As CellElement
        Set oCell = CreateCellElement2(MARKER_CELL_NAME, current, Point3dOne, True, rotation)
        ActiveModelReference.AddElement oCell
    Next n
    msg = "Placed " & CStr(nMarkers) & " markers along element"
    ShowMessage msg, msg, msdMessageCenterPriorityInfo
    Exit Function
    
err_CreateMarkers:
    ReportError MODULE_NAME, "CreateMarkers"
End Function
' ---------------------------------------------------------------------

Attribute VB_Name = "modMain"
Option Explicit
' ---------------------------------------------------------------------
Private Const MODULE_NAME                   As String = "modMain"
Private Const VERSION_                      As String = "18.06.14"
' ---------------------------------------------------------------------
'   The marker cell is hard-wired here.  If you want to use a different
'   cell, change its name here.
' ---------------------------------------------------------------------
Public Const MARKER_CELL_NAME               As String = "Sleeper"
' ---------------------------------------------------------------------
'   Notice:
'   Software developed by LA Solutions Ltd for demonstration purposes.
'   This software places a mark (e.g. text or cell) at regular spacing
'   along a linear element.
'   This project demonstrates how to calculate a point at a distance along
'   a line and derive the tangent to the line at that point.
'   The tool works either interactively, when it shows a cell placed at
'   the nearest point on the chosen line.
'   Alternatively, the tool works automatically once user has chosen a line,
'   and places a number of cells at a regular spacing along the element.
'
'   LA Solutions Ltd grants you the right to use this VBA code for any
'   use, personal or commercial, provided that this notice is retained in full.
'
'   www.la-solutions.co.uk
'
'   End of Notice
' ---------------------------------------------------------------------
'   References (menu Tools|References):
'   None
' ---------------------------------------------------------------------
'   Version History:
'   18.06.14        initial prototype
' ---------------------------------------------------------------------
Public Function Version() As String
    Version = VERSION_
End Function
' ---------------------------------------------------------------------
'   modMain
'   Main entry point.  Default mode is to place a number of cells along
'   a chosen line.
'   key-in:
'   VBA RUN [FollowLine]modMain.Main
'   or
'   VBA RUN [FollowLine]modMain.Main interactive
' ---------------------------------------------------------------------
Public Sub Main()
    On Error GoTo err_Main
    Dim msg                                 As String
    msg = "Follow Line version " & Version()
    ShowMessage msg, "FollowLine created by LA Solutions Ltd", msdMessageCenterPriorityInfo, False
    Debug.Print msg
    Dim oLinePicker                         As New clsLinePicker
    oLinePicker.Interactive = False
    If vbNullString <> KeyinArguments Then
        If 0 = StrComp("Interactive", KeyinArguments, vbTextCompare) Then
            oLinePicker.Interactive = True
        End If
    End If
    oLinePicker.Spacing = 0.5
    CommandState.StartLocate oLinePicker
    Exit Sub
    
err_Main:
    ReportError MODULE_NAME, "Main"
End Sub
' ---------------------------------------------------------------------
'   Quote
'   Wrap a string in single quotes
' ---------------------------------------------------------------------
Public Function Quote(ByVal s As String) As String
    Const SingleQuote                       As String = "'"
    Quote = SingleQuote & s & SingleQuote
End Function
' ---------------------------------------------------------------------
'   ReportError
'   Generic error reporting
' ---------------------------------------------------------------------
Public Sub ReportError(ByVal moduleName As String, ByVal procName As String)
    MsgBox "Error no. " & CStr(Err.Number) & ": " & Err.Description & vbNewLine & _
        "Caused by " & Err.Source, vbOKCancel Or vbExclamation, "Error in " & moduleName & ":" & procName
End Sub
' ---------------------------------------------------------------------
