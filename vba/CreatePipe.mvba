Attribute VB_Name = "clsPipePlacerCone"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
' ---------------------------------------------------------------------
Private Const MODULE_NAME                   As String = "clsPipePlacerCone"
' ---------------------------------------------------------------------
'   This primitive class creates a pipe using a cone having identical
'   top and bottom radii
' ---------------------------------------------------------------------
Implements IPrimitiveCommandEvents
' ---------------------------------------------------------------------
Private m_oParent                           As frmCreatePipe
Private m_ptBase                            As Point3d
Private m_dblLength                         As Double
'Private m_dblRadius                         As Double ' Radius is obtained dynamically from frmCreatePipe
Private m_nPointCount                       As Long
' ---------------------------------------------------------------------
Public Property Let Length(ByVal d As Double)
    m_dblLength = d
End Property
Public Property Get Length() As Double
    Length = m_dblLength
End Property
' ---------------------------------------------------------------------
'Public Property Let Radius(ByVal d As Double)
'    m_dblRadius = d
'End Property
'Public Property Let Diameter(ByVal d As Double)
'    m_dblRadius = d / 2#
'End Property
' ---------------------------------------------------------------------
Public Property Set Parent(ByVal oFrm As frmCreatePipe)
    Set m_oParent = oFrm
End Property
' ---------------------------------------------------------------------
Private Sub IPrimitiveCommandEvents_Cleanup()
    m_nPointCount = 0
    CommandState.StopDynamics
End Sub
' ---------------------------------------------------------------------
Private Function GetRadius() As Double
    Dim d                                   As Double
    d = m_oParent.Diameter
    GetRadius = d / 2#
End Function
' ---------------------------------------------------------------------
Private Sub IPrimitiveCommandEvents_DataPoint(Point As Point3d, ByVal oView As View)
    Debug.Print "Have " & CStr(m_nPointCount) & " points"
    If 0 = m_nPointCount Then
        m_ptBase = Point
        ShowPrompt "Datapoint end or direction of pipe"
        CommandState.StartDynamics
        m_nPointCount = 1 + m_nPointCount
    ElseIf 1 = m_nPointCount Then
        Dim oPipe                           As Element
        Set oPipe = ConstructPipeCone(m_ptBase, Point, GetRadius(), msdDrawingModeNormal)
        ActiveModelReference.AddElement oPipe
        m_oParent.Length = Point3dDistance(m_ptBase, Point)
        m_nPointCount = 0
        m_ptBase = Point '   Start next pipe from end of this one
        CommandState.AccuDrawHints.SetOrigin m_ptBase
        ShowPrompt "Datapoint start of pipe"
        CommandState.StopDynamics
    End If
End Sub
' ---------------------------------------------------------------------
Private Sub IPrimitiveCommandEvents_Dynamics(Point As Point3d, ByVal oView As View, ByVal drawMode As MsdDrawingMode)
    Dim oPipe                               As Element
    Set oPipe = ConstructPipeCone(m_ptBase, Point, GetRadius(), drawMode)
End Sub
' ---------------------------------------------------------------------
'   ConstructPipeCone
'   Construct a pipe as a cone element having identical top & bottom radii.
'   Alternatively, create a SmartSolid cone element like this:
'   Set SmartSolidElement = object.CreateCone (Template, topRadius, baseRadius, height)
' ---------------------------------------------------------------------
Private Function ConstructPipeCone(ByRef startPoint As Point3d, ByRef endPoint As Point3d, ByVal radius As Double, ByVal drawMode As MsdDrawingMode) As Element
    Set ConstructPipeCone = Nothing
    On Error GoTo err_ConstructPipeCone
    '   Pipe is a cone having equal radii ends
    Dim oCone                               As ConeElement
    Set oCone = CreateConeElement1(Nothing, radius, startPoint, radius, endPoint, Matrix3dIdentity)
    oCone.Redraw drawMode
    Set ConstructPipeCone = oCone
    Exit Function

err_ConstructPipeCone:
    ReportError MODULE_NAME, "ConstructPipeCone"
End Function
' ---------------------------------------------------------------------
Private Sub IPrimitiveCommandEvents_Keyin(ByVal Keyin As String)

End Sub
' ---------------------------------------------------------------------
Private Sub IPrimitiveCommandEvents_Reset()
    m_nPointCount = 0
    CommandState.StopDynamics
    CommandState.StartDefaultCommand
End Sub
' ---------------------------------------------------------------------
Private Sub IPrimitiveCommandEvents_Start()
    CommandState.CommandName = "Place Pipe" & " (cone)"
    ShowCommand CommandState.CommandName
    ShowPrompt "Datapoint start of pipe"
    m_nPointCount = 0
End Sub
' ---------------------------------------------------------------------

Attribute VB_Name = "clsPipePlacerExtrusion"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
' ---------------------------------------------------------------------
Private Const MODULE_NAME                   As String = "clsPipePlacerExtrusion"
' ---------------------------------------------------------------------
'   This primitive class creates a pipe using an extruded circle
' ---------------------------------------------------------------------
Implements IPrimitiveCommandEvents
' ---------------------------------------------------------------------
Private m_oParent                           As frmCreatePipe
Private m_ptBase                            As Point3d
Private m_dblLength                         As Double
'Private m_dblRadius                         As Double ' Radius is obtained dynamically from frmCreatePipe
Private m_nPointCount                       As Long
' ---------------------------------------------------------------------
Public Property Let Length(ByVal d As Double)
    m_dblLength = d
End Property
Public Property Get Length() As Double
    Length = m_dblLength
End Property
' ---------------------------------------------------------------------
'Public Property Let Radius(ByVal d As Double)
'    m_dblRadius = d
'End Property
'Public Property Let Diameter(ByVal d As Double)
'    m_dblRadius = d / 2#
'End Property
' ---------------------------------------------------------------------
Public Property Set Parent(ByVal oFrm As frmCreatePipe)
    Set m_oParent = oFrm
End Property
' ---------------------------------------------------------------------
Private Sub IPrimitiveCommandEvents_Cleanup()
    m_nPointCount = 0
    CommandState.StopDynamics
End Sub
' ---------------------------------------------------------------------
Private Function GetRadius() As Double
    Dim d                                   As Double
    d = m_oParent.Diameter
    GetRadius = d / 2#
End Function
' ---------------------------------------------------------------------
Private Sub IPrimitiveCommandEvents_DataPoint(Point As Point3d, ByVal oView As View)
    Debug.Print "Have " & CStr(m_nPointCount) & " points"
    If 0 = m_nPointCount Then
        m_ptBase = Point
        ShowPrompt "Datapoint end or direction of pipe"
        CommandState.StartDynamics
        m_nPointCount = 1 + m_nPointCount
    ElseIf 1 = m_nPointCount Then
        Dim oPipe                           As Element
        Set oPipe = ConstructPipeExtrusion(m_ptBase, Point, GetRadius(), msdDrawingModeNormal)
        ActiveModelReference.AddElement oPipe
        m_oParent.Length = Point3dDistance(m_ptBase, Point)
        m_nPointCount = 0
        m_ptBase = Point '   Start next pipe from end of this one
        CommandState.AccuDrawHints.SetOrigin m_ptBase
        ShowPrompt "Datapoint start of pipe"
        CommandState.StopDynamics
    End If
End Sub
' ---------------------------------------------------------------------
Private Sub IPrimitiveCommandEvents_Dynamics(Point As Point3d, ByVal oView As View, ByVal drawMode As MsdDrawingMode)
    Dim oPipe                               As Element
    Set oPipe = ConstructPipeExtrusion(m_ptBase, Point, GetRadius(), drawMode)
End Sub
' ---------------------------------------------------------------------
'   ConstructPipeExtrusion
'   Construct a pipe as an extruded circle.
' ---------------------------------------------------------------------
Private Function ConstructPipeExtrusion(ByRef startPoint As Point3d, ByRef endPoint As Point3d, ByVal radius As Double, ByVal drawMode As MsdDrawingMode) As Element
    Set ConstructPipeExtrusion = Nothing
    On Error GoTo err_ConstructPipeExtrusion
    Dim oPipe                               As SmartSolidElement
    Set oPipe = ExtrudePipe(startPoint, endPoint, radius)
    oPipe.Redraw drawMode
    
    Set ConstructPipeExtrusion = oPipe
    Exit Function

err_ConstructPipeExtrusion:
    ReportError MODULE_NAME, "ConstructPipeExtrusion"
End Function
' ---------------------------------------------------------------------
'   ExtrudePipe
'   Create a cylinder of known radius and height.
'   This is created at the origin of the 3D world.  We need to move the
'   new cylinder to its correct location and orientation
'   There seems to be a minimum distance for the cylinder height.  Calling with
'   too small a height creates a run-time error
'   Error no. -2147212432: msdError -9072
' ---------------------------------------------------------------------
Private Function ExtrudePipe(ByRef base As Point3d, ByRef top As Point3d, ByVal radius As Double) As SmartSolidElement
    Set ExtrudePipe = Nothing
    On Error GoTo err_ExtrudePipe
    Const MinHeight                         As Double = 10    '   Arbitrary choice
    Dim height                              As Double
    height = Point3dDistance(base, top)
    height = IIf(height < MinHeight, MinHeight, height)
    Dim oPipe                               As SmartSolidElement
    Set oPipe = SmartSolid.CreateCylinder(Nothing, radius, height)
    '   Move the pipe from origin to base point
    Dim transform                           As Transform3d
    transform = Transform3dFromPoint3d(base)
    '   Rotate the pipe by the angle (rotation matrix) from base to top
    Dim direction                           As Point3d
    direction = Point3dSubtract(base, top)
    '   The X-axis projected from base point
    Dim axis                                As Point3d
    axis = Point3dAdd(base, Point3dFromXYZ(1, 0, 0))
    Dim rotation                            As Matrix3d
    rotation = Matrix3dFromRotationBetweenVectors(axis, direction)
    transform = Transform3dFromMatrix3dPoint3d(rotation, base)
    oPipe.transform transform
    Set ExtrudePipe = oPipe
    Exit Function
    
err_ExtrudePipe:
    ReportError MODULE_NAME, "ExtrudePipe"
End Function
' ---------------------------------------------------------------------
Private Sub IPrimitiveCommandEvents_Keyin(ByVal Keyin As String)

End Sub
' ---------------------------------------------------------------------
Private Sub IPrimitiveCommandEvents_Reset()
    m_nPointCount = 0
    CommandState.StopDynamics
    CommandState.StartDefaultCommand
End Sub
' ---------------------------------------------------------------------
Private Sub IPrimitiveCommandEvents_Start()
    CommandState.CommandName = "Place Pipe" & " (extrusion)"
    ShowCommand CommandState.CommandName
    ShowPrompt "Datapoint start of pipe"
    m_nPointCount = 0
End Sub
' ---------------------------------------------------------------------

Attribute VB_Name = "frmCreatePipe"
Attribute VB_Base = "0{3F76A8E8-E924-4530-93B6-FA72F6F355E3}{19D15CBD-B252-4FAE-A7E1-2DA5CE7F86CE}"
Attribute VB_GlobalNameSpace = False
Attribute VB_Creatable = False
Attribute VB_PredeclaredId = True
Attribute VB_Exposed = False
Attribute VB_TemplateDerived = False
Attribute VB_Customizable = False
Option Explicit
' ---------------------------------------------------------------------
Private Const MODULE_NAME                   As String = "frmCreatePipe"
' ---------------------------------------------------------------------
Private m_dblDiameter                       As Double
Private m_dblLength                         As Double
' ---------------------------------------------------------------------
Private Function FormatDouble2Decimal(ByVal d As Double) As String
    FormatDouble2Decimal = Format(d, "#,##0.00")
End Function
' ---------------------------------------------------------------------
Public Property Let Length(ByVal d As Double)
    If 0# < d Then
        m_dblLength = d
        txtPipeLength.Text = FormatDouble2Decimal(d)
    Else
        Dim msg                             As String
        msg = "Length may not be negative"
        ShowMessage msg, msg, msdMessageCenterPriorityWarning, False
    End If
End Property
' ---------------------------------------------------------------------
Public Property Get Length() As Double
    Length = m_dblLength
End Property
' ---------------------------------------------------------------------
Public Property Let Diameter(ByVal d As Double)
    If 0# < d Then
        m_dblDiameter = d
        txtPipeDiameter.Text = FormatDouble2Decimal(d)
    Else
        Dim msg                             As String
        msg = "Diameter may not be negative"
        ShowMessage msg, msg, msdMessageCenterPriorityWarning, False
    End If
End Property
' ---------------------------------------------------------------------
Public Property Get Diameter() As Double
    Diameter = m_dblDiameter
End Property
' ---------------------------------------------------------------------
'   cmdPlacePipeCone
'   Start a MicroStation primitive class to place a pipe
' ---------------------------------------------------------------------
Private Sub cmdPlacePipeCone_Click()
    Dim oPipePlacer                         As New clsPipePlacerCone
    Set oPipePlacer.Parent = Me
    'oPipePlacer.Diameter = Diameter
    oPipePlacer.Length = Length
    CommandState.StartPrimitive oPipePlacer
End Sub
' ---------------------------------------------------------------------
'   cmdPlacePipeExtrusion
'   Start a MicroStation primitive class to place a pipe
' ---------------------------------------------------------------------
Private Sub cmdPlacePipeExtrusion_Click()
    Dim oPipePlacer                         As New clsPipePlacerExtrusion
    Set oPipePlacer.Parent = Me
    'oPipePlacer.Diameter = Diameter
    oPipePlacer.Length = Length
    CommandState.StartPrimitive oPipePlacer
End Sub
' ---------------------------------------------------------------------
Private Sub txtPipeDiameter_Exit(ByVal Cancel As MSForms.ReturnBoolean)
    Dim d                                   As Double
    If CheckPositiveNumber(d, "pipe diameter", txtPipeDiameter.Text) Then
        Diameter = d
    End If
    Cancel = False
End Sub
' ---------------------------------------------------------------------
Private Sub txtPipeLength_Exit(ByVal Cancel As MSForms.ReturnBoolean)
    Dim d                                   As Double
    If CheckPositiveNumber(d, "pipe length", txtPipeLength.Text) Then
        Length = d
    End If
    Cancel = False
End Sub
' ---------------------------------------------------------------------
'   CheckPositiveNumber
'   Validate user input: must be a number; must be positive
'   Returns:    True if proposed is a valid positive number
' ---------------------------------------------------------------------
Private Function CheckPositiveNumber(ByRef result As Double, ByVal what As String, ByVal proposed As String) As Boolean
    CheckPositiveNumber = False
    result = 0#
    Dim msg                                 As String
    If IsNumeric(proposed) Then
        Dim d                               As Double
        d = CDbl(proposed)
        If 0 < d Then
            result = d
            CheckPositiveNumber = True
        Else
            msg = "Please enter a positive number for " & what
            ShowMessage msg, msg, msdMessageCenterPriorityError, False
        End If
    Else
        msg = "Please enter a number for " & what
        ShowMessage msg, msg, msdMessageCenterPriorityError, False
    End If
End Function
' ---------------------------------------------------------------------
Private Sub UserForm_Initialize()
    Me.lblVersion.Caption = "Version: " & Version()
    Diameter = 10#
    Length = 20#
End Sub
' ---------------------------------------------------------------------

Attribute VB_Name = "modMain"
Option Explicit
' ---------------------------------------------------------------------
Private Const MODULE_NAME                   As String = "modMain"
Private Const VERSION_                      As String = "16.1.18.1"
' ---------------------------------------------------------------------
'   Notice:
'
'   VBA project CreatePipe is provided as-is with no guarantee of
'   suitability for purpose.  CreatePipe is provided as FreeWare.
'   No copyright is claimed and no license fee is payable.
'   Use at your own risk.
'
'   CreatePipe is provided to demonstrate the use of MicroStation VBA
'   to solve a particular task.  The question asked was
'   "How do I create a pipe or cylinder in a DGN model?"
'
'   The example shows two ways to create a pipe:
'       As a cone having equal top & bottom radii
'       As an extruded circle
'
'   CreatePipe.mvba was developed by LA Solutions Ltd.
'   Visit our web site:
'   www.la-solutions.co.uk
'
'   You may use this sample code for any purpose provided that this notice
'   is retained in full.
'
'   End of Notice
' ---------------------------------------------------------------------
'   References
'
' ---------------------------------------------------------------------
'   Main entry point
'   key-in:
'   vba run [CreatePipe]modMain.Main
' ---------------------------------------------------------------------
Public Sub Main()
    On Error GoTo err_Main
    Debug.Print "[CreatePipe]modMain.Main version " & Version()
    If ActiveModelReference.Is3D Then
        frmCreatePipe.Show vbModeless
    Else
        Dim msg                             As String
        msg = "This is not a 3D model.  To place a pipe, first open a 3D model"
        ShowMessage msg, msg, msdMessageCenterPriorityInfo, True
    End If
    Exit Sub
    
err_Main:
    ReportError MODULE_NAME, "Main"
End Sub
' ---------------------------------------------------------------------
Public Function Version() As String
    Version = VERSION_
End Function
' ---------------------------------------------------------------------
'   ReportError
'   Report errors in a consistent manner
' ---------------------------------------------------------------------
Public Sub ReportError(ByVal moduleName As String, ByVal procName As String)
    MsgBox "Error no. " & CStr(Err.Number) & ": " & Err.Description & vbNewLine & "Caused by " & Err.Source, vbOKOnly Or vbExclamation, "Error in " & moduleName & ":" & procName
End Sub
' ---------------------------------------------------------------------
