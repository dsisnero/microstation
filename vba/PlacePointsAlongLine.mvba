Attribute VB_Name = "clsLineLocator"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
' ---------------------------------------------------------------------
Private Const MODULE_NAME                   As String = "clsLineLocator"
' ---------------------------------------------------------------------
Private m_oParent                           As frmPlacePointsAlongLine
' ---------------------------------------------------------------------
Implements ILocateCommandEvents
' ---------------------------------------------------------------------
Public Property Set Parent(ByVal oParent As UserForm)
    Set m_oParent = oParent
End Property
' ---------------------------------------------------------------------
Private Sub Class_Initialize()
End Sub
' ---------------------------------------------------------------------
Private Sub ILocateCommandEvents_Accept(ByVal oElement As Element, point As Point3d, ByVal oView As View)
    Debug.Print "Accepted element type " & CStr(oElement.Type)
    Dim startPoint                          As Point3d
    Dim length                              As Double
    length = 0#
    GetElementParams length, startPoint, oElement
    Debug.Assert Not m_oParent Is Nothing
    m_oParent.txtLength.Text = Format(length, "0.00")
    Set m_oParent.line = oElement
    MarkElementStart oElement, m_oParent.MarkerSize, m_oParent.Transients
End Sub
' ---------------------------------------------------------------------
Private Sub GetElementParams(ByRef length As Double, ByRef startPoint As Point3d, ByVal oElement As Element)
    Select Case oElement.Type
    Case msdElementTypeArc
        length = oElement.AsArcElement.length
        startPoint = oElement.AsArcElement.startPoint
    Case msdElementTypeLine, msdElementTypeLineString
        length = oElement.AsLineElement.length
        startPoint = oElement.AsLineElement.startPoint
    Case msdElementTypeBsplineCurve
        length = oElement.AsBsplineCurveElement.length
        startPoint = oElement.AsBsplineCurveElement.startPoint
    Case msdElementTypeComplexString
        length = oElement.AsComplexStringElement.length
        startPoint = oElement.AsComplexStringElement.startPoint
    End Select
End Sub
' ---------------------------------------------------------------------
Private Sub ILocateCommandEvents_Cleanup()

End Sub
' ---------------------------------------------------------------------
Private Sub ILocateCommandEvents_Dynamics(point As Point3d, ByVal oView As View, ByVal drawMode As MsdDrawingMode)

End Sub
' ---------------------------------------------------------------------
Private Sub ILocateCommandEvents_LocateFailed()
    ShowStatus "Not a suitable linear element"
End Sub
' ---------------------------------------------------------------------
Private Sub ILocateCommandEvents_LocateFilter(ByVal oElement As Element, point As Point3d, accepted As Boolean)
    '   Lines, line-strings and complex strings are Vertex Lists
    ' accepted = oElement.IsVertexList ' IsVertexList returns False for a complex string, even though it's documented as valid
    accepted = ElementSupportsPointAtDistance(oElement)
End Sub
' ---------------------------------------------------------------------
Private Sub ILocateCommandEvents_LocateReset()

End Sub
' ---------------------------------------------------------------------
Private Sub ILocateCommandEvents_Start()
    CommandState.commandName = "Place Points at Distance along Line"
    ShowCommand CommandState.commandName
    ShowPrompt "Pick a line"
    
    Dim oLocateCriteria                     As LocateCriteria
    '  Since this command does not modify the original element,
    '  set the locate criteria to allow  read-only elements.
    Set oLocateCriteria = CommandState.CreateLocateCriteria(False)
    CommandState.SetLocateCriteria oLocateCriteria
    m_oParent.EraseMarker
End Sub
' ---------------------------------------------------------------------

Attribute VB_Name = "clsTransactionWrapper"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
' ---------------------------------------------------------------------
Private Const MODULE_NAME                   As String = "clsTransactionWrapper"
' ---------------------------------------------------------------------
'   Use this wrapper to bracket a sequence of element creation or modification
'   steps that you want to consider a single transaction.
'   This enables the user to undo that set of steps from MicroStation's Edit|Undo menu
'
'   For a usage example, see frmPlacePointsAlongLine.PlacePoints
' ---------------------------------------------------------------------
'   StartUndoableTransaction
'   The command name appears in MicroStation's Edit|Undo menu
' ---------------------------------------------------------------------
Public Sub StartUndoableTransaction(ByVal name As String)
    CommandState.commandName = name
End Sub
' ---------------------------------------------------------------------
Private Sub Class_Terminate()
    CommandState.StartDefaultCommand
End Sub
' ---------------------------------------------------------------------

Attribute VB_Name = "frmPlacePointsAlongLine"
Attribute VB_Base = "0{9D64082C-3908-4DDA-A059-25B816BD4E6D}{14657280-20F7-43E0-8907-5A94C964B7FA}"
Attribute VB_GlobalNameSpace = False
Attribute VB_Creatable = False
Attribute VB_PredeclaredId = True
Attribute VB_Exposed = False
Attribute VB_TemplateDerived = False
Attribute VB_Customizable = False
Option Explicit
' ---------------------------------------------------------------------
Private Const MODULE_NAME                   As String = "frmPlacePointsAlongLine"
' ---------------------------------------------------------------------
Private m_oTransients                       As TransientElementContainer
Private m_oLine                             As Element
Private m_dblData()                         As Double
Private m_strPointCell                      As String
' ---------------------------------------------------------------------
Public Property Set line(ByVal oLine As Element)
    Set m_oLine = oLine
End Property
' ---------------------------------------------------------------------
Public Property Get Transients() As TransientElementContainer
    Set Transients = m_oTransients
End Property
' ---------------------------------------------------------------------
'   MarkerSize
'   Return the numeric value of the marker size text box
' ---------------------------------------------------------------------
Public Property Get MarkerSize() As Double
    Dim size                                As String
    size = txtMarkerSize.Text
    If 0 = Len(size) Then size = "1.0"
    MarkerSize = CDbl(size)
End Property
' ---------------------------------------------------------------------
'   EraseMarker
'   Remove the transient marker that indicates the end of a selected line
' ---------------------------------------------------------------------
Public Sub EraseMarker()
    Debug.Assert Not m_oTransients Is Nothing
    m_oTransients.Reset
End Sub
' ---------------------------------------------------------------------
Private Sub PointCellName()
    If chkPointCell.Value Then
        m_strPointCell = ActiveSettings.PointCellName
    Else
        m_strPointCell = txtPointCell.Text
    End If
    Dim msg                                 As String
    msg = "Point cell is '" & m_strPointCell & "'"
    ShowMessage msg, msg, msdMessageCenterPriorityInfo, False
    Debug.Print msg
End Sub

' ---------------------------------------------------------------------
Private Sub chkPointCell_Click()
    PointCellName
End Sub
' ---------------------------------------------------------------------
Private Sub cmdChangeEnd_Click()
    Dim msg                                 As String
    If m_oLine Is Nothing Then
        '   Nothing to do
        msg = "Pick a line first"
        ShowMessage msg, msg, msdMessageCenterPriorityWarning, False
    Else
        Dim valid                           As Boolean
        valid = True
        EraseMarker
        If ReverseElement(m_oLine) Then MarkElementStart m_oLine, MarkerSize, m_oTransients
    End If
End Sub
' ---------------------------------------------------------------------
'   cmdFileOpen_Click
'   Open a CSV file and attempt to parse data
' ---------------------------------------------------------------------
Private Sub cmdFileOpen_Click()
    Dim msg                                 As String
    Dim fileName                            As String
    Dim dgnFolder                           As String
    dgnFolder = ActiveWorkspace.ConfigurationVariableValue("MS_DEF")
    If FileOpen(fileName, dgnFolder, "Open CSV File") Then
        txtDataFile.Text = fileName
        Dim nPoints                         As Long
        nPoints = ParseDistanceFile(m_dblData, fileName)
        If 0 = nPoints Then
            msg = "No points found in data file"
            ShowMessage msg, fileName, msdMessageCenterPriorityWarning, True
        Else
            msg = "Parsed " & CStr(nPoints) & " points from data file"
            ShowMessage msg, fileName, msdMessageCenterPriorityInfo, False
            TracePoints
        End If
        Debug.Print msg
    Else
        txtDataFile.Text = vbNullString
    End If
End Sub
' ---------------------------------------------------------------------
'   TracePoints
'   Useful during development
' ---------------------------------------------------------------------
Sub TracePoints()
    Dim nPoints                             As Long
    nPoints = ArraySize(m_dblData)
    Dim n                                   As Long
    For n = LBound(m_dblData, 1) To nPoints - 1
        Debug.Print "Point [" & CStr(n) & "]=" & Format(m_dblData(n), "0.00")
    Next n
End Sub
' ---------------------------------------------------------------------
Private Sub cmdPickLine_Click()
    txtLength.Text = "0.0"
    EraseMarker
    Dim oLineLocator                        As New clsLineLocator
    Set oLineLocator.Parent = Me
    CommandState.StartLocate oLineLocator
End Sub
' ---------------------------------------------------------------------
'   cmdPlacePoints_Click
'   Check that we have a line and some points before starting point creation
' ---------------------------------------------------------------------
Private Sub cmdPlacePoints_Click()
    txtPointsPlaced.Text = CStr(0)
    Dim msg                                 As String
    Dim nPoints                             As Long
    nPoints = ArraySize(m_dblData)
    If (0 < nPoints) Then
        If Not m_oLine Is Nothing Then
            If 0 < Len(m_strPointCell) Then
                Dim nPlaced                 As Long
                '   Everything seems to be OK
                nPlaced = PlacePoints(m_strPointCell, chkCreateTangent.Value)
                txtPointsPlaced.Text = CStr(nPlaced)
                msg = "Placed " & CStr(nPlaced) & " points. "
                If nPlaced = nPoints Then
                    msg = "All points were placed"
                Else
                    msg = CStr(nPoints - nPlaced) & " points fell off the line"
                End If
                ShowMessage msg, msg, msdMessageCenterPriorityInfo, False
                Debug.Print msg
            Else
                msg = "Specify a valid cell or point cell before placing points!"
                ShowMessage msg, msg, msdMessageCenterPriorityWarning, False
            End If
        Else
            msg = "Pick a line before placing points!"
            ShowMessage msg, msg, msdMessageCenterPriorityWarning, False
        End If
    Else
        msg = "No points to place!"
        ShowMessage msg, msg, msdMessageCenterPriorityWarning, False
    End If
End Sub
' ---------------------------------------------------------------------
'   PlacePoints
'   Do the work of creating points (cells).
'   If createTangents is True, then calculate the tangent at each point
'   and draw a line representing that tangent
' ---------------------------------------------------------------------
Private Function PlacePoints(ByVal cellName As String, ByVal createTangents As Boolean) As Long
    PlacePoints = 0
    On Error GoTo err_PlacePoints
    Dim nPoints                             As Long
    nPoints = ArraySize(m_dblData)
    Dim oWrapper                            As New clsTransactionWrapper
    oWrapper.StartUndoableTransaction "Place Points at Distance along Line"
    '   Apply the same Graphic Group number to each point
    Dim graphicGroup                        As Long
    graphicGroup = Application.UpdateGraphicGroupNumber
    Dim origin                              As Point3d
    Dim cellScale                           As Point3d
    cellScale = ActiveSettings.Scale
    Dim nPlaced                             As Long
    nPlaced = 0
    '   We need a temporary B-spline to compute tangent points
    Dim oSpline                             As New BsplineCurve
    oSpline.FromElement m_oLine
    Dim oSplineElement                      As BsplineCurveElement
    Set oSplineElement = CreateBsplineCurveElement1(Nothing, oSpline)
    Const TangentColour                     As Long = 78 ' Brown
    Dim n                                   As Long
    For n = 0 To nPoints - 1
        If PointAtDistance(origin, m_oLine, m_dblData(n)) Then
            Dim oMark                       As CellElement
            Set oMark = CreateCellElement2(cellName, origin, cellScale, True, Matrix3dIdentity)
            '   Each point on the current line has the same graphic group
            oMark.graphicGroup = graphicGroup
            oMark.ConvertToPointCell
            ActiveModelReference.AddElement oMark
            If createTangents Then
                '   Create tangent
                Dim oTangent                As LineElement
                Dim hitPoint                As Point3d
                Set oTangent = CreateTangentAtPoint(oSplineElement, m_dblData(n))
                If Not oTangent Is Nothing Then
                    oTangent.ScaleUniform origin, MarkerSize() / oTangent.length
                    oTangent.graphicGroup = graphicGroup
                    oTangent.Color = TangentColour
                    ActiveModelReference.AddElement oTangent
                End If
            End If
            nPlaced = 1 + nPlaced
        End If
    Next n
    PlacePoints = nPlaced
    Set oSplineElement = Nothing
    Set oSpline = Nothing
    Exit Function
    
err_PlacePoints:
    ReportError MODULE_NAME, "PlacePoints"
End Function
' ---------------------------------------------------------------------
'   CreateTangentAtPoint
' ---------------------------------------------------------------------
Function CreateTangentAtPoint(ByVal oSplineElement As BsplineCurveElement, ByVal distance As Double) As LineElement
    Set CreateTangentAtPoint = Nothing
    On Error GoTo err_CreateTangentAtPoint
    Dim position                            As Point3d
    Dim tangent                             As Point3d
    If PointAtDistanceAlongElement(position, tangent, distance, oSplineElement) Then
        Dim points(0 To 1)                  As Point3d
        points(0) = Point3dSubtract(position, tangent)
        points(1) = Point3dAdd(position, tangent)
        Set CreateTangentAtPoint = CreateLineElement1(Nothing, points)
    End If
    Exit Function
    
err_CreateTangentAtPoint:
    ReportError MODULE_NAME, "CreateTangentAtPoint"
End Function
' ---------------------------------------------------------------------
'   PointAtDistance
'   Calculate a point at a distance along an element.  The element must
'   support the PointAtDistance method.
'   As an additional check, verify that the distance is a positive value
'   that does not exceed the length of the element
'   Returns True if a valid point was calculated
' ---------------------------------------------------------------------
Public Function PointAtDistance(ByRef origin As Point3d, ByVal oElement As Element, ByVal distance As Double) As Boolean
    PointAtDistance = False
    On Error GoTo err_PointAtDistance
    
    Dim valid                               As Boolean
    valid = False
    Dim length                              As Double
    Select Case oElement.Type
    Case msdElementTypeComplexString
        origin = oElement.AsComplexStringElement.PointAtDistance(distance)
        valid = distance < oElement.AsComplexStringElement.length
    Case msdElementTypeLine, msdElementTypeLineString
        origin = oElement.AsLineElement.PointAtDistance(distance)
        valid = distance < oElement.AsLineElement.length
    Case msdElementTypeArc
        origin = oElement.AsArcElement.PointAtDistance(distance)
        valid = distance < oElement.AsArcElement.length
    Case msdElementTypeBsplineCurve
        origin = oElement.AsBsplineCurveElement.PointAtDistance(distance)
        valid = distance < oElement.AsBsplineCurveElement.length
    End Select
    PointAtDistance = valid
    
    Exit Function
    
err_PointAtDistance:
    ReportError MODULE_NAME, "PointAtDistance"
End Function
' ---------------------------------------------------------------------
Private Sub UserForm_Initialize()
    Dim flags                               As MsdTransientFlags
    flags = msdTransientFlagsOverlay + msdTransientFlagsSnappable
    Set m_oTransients = CreateTransientElementContainer1(Nothing, flags, msdViewAll, msdDrawingModeNormal)
    txtDataFile.Text = "point-distances.csv" '   You probably want to change this default data file name
    txtPointCell.Text = "Ext Metal Loss"    '   You probably want to change this default point cell name
    chkPointCell.Value = True
    chkCreateTangent.Value = True
    txtMarkerSize.Text = Format(1, "0.00")
    PointCellName
    txtVersion.Text = "Version: " & Version()
End Sub
' ---------------------------------------------------------------------
Private Sub UserForm_Terminate()
    Set m_oTransients = Nothing
End Sub
' ---------------------------------------------------------------------

Attribute VB_Name = "modCommonDialog"
Option Explicit
' ---------------------------------------------------------------------
Private Const MODULE_NAME                   As String = "modCommonDialog"
' ---------------------------------------------------------------------
'   This module wraps the code required to use the Windows Common Dialogs,
'   specifically the File Open dialog, from MicroStation VBA
' ---------------------------------------------------------------------
Private Declare Function GetOpenFileName Lib "comdlg32.dll" Alias _
         "GetOpenFileNameA" (pOpenfilename As OPENFILENAME) As Long

Private Type OPENFILENAME
  lStructSize As Long
  hwndOwner As Long
  hInstance As Long
  lpstrFilter As String
  lpstrCustomFilter As String
  nMaxCustFilter As Long
  nFilterIndex As Long
  lpstrFile As String
  nMaxFile As Long
  lpstrFileTitle As String
  nMaxFileTitle As Long
  lpstrInitialDir As String
  lpstrTitle As String
  flags As Long
  nFileOffset As Integer
  nFileExtension As Integer
  lpstrDefExt As String
  lCustData As Long
  lpfnHook As Long
  lpTemplateName As String
End Type

Public Const OFN_ALLOWMULTISELECT = &H200&
Public Const OFN_EXPLORER = &H80000
Public Const OFN_FILEMUSTEXIST = &H1000&
Public Const OFN_HIDEREADONLY = &H4&
Public Const OFN_PATHMUSTEXIST = &H800&

' ---------------------------------------------------------------------
'   FileOpen
' ---------------------------------------------------------------------
Public Function FileOpen(ByRef fileName As String, ByVal initialFolder As String, ByVal caption As String) As Boolean
    FileOpen = False
    On Error GoTo err_FileOpen
    
    Dim OpenFile                            As OPENFILENAME
    Dim lReturn                             As Long
    Dim sFilter                             As String
    OpenFile.lStructSize = Len(OpenFile)
    'OpenFile.hwndOwner = ?
    OpenFile.hInstance = 0
    sFilter = "CSV Files (*.csv)" & Chr(0) & "*.CSV" & Chr(0)
    OpenFile.lpstrFilter = sFilter
    OpenFile.nFilterIndex = 1
    OpenFile.lpstrFile = String(257, 0)
    OpenFile.nMaxFile = Len(OpenFile.lpstrFile) - 1
    OpenFile.lpstrFileTitle = OpenFile.lpstrFile
    OpenFile.nMaxFileTitle = OpenFile.nMaxFile
    OpenFile.lpstrInitialDir = initialFolder
    OpenFile.lpstrTitle = caption
    OpenFile.flags = OFN_PATHMUSTEXIST + OFN_FILEMUSTEXIST + OFN_EXPLORER
    lReturn = GetOpenFileName(OpenFile)
    If lReturn = 0 Then
       Debug.Print "The User pressed the Cancel Button"
    Else
        Dim filePos                         As Long
        filePos = InStr(1, OpenFile.lpstrFile, Chr(0))
        fileName = Left(OpenFile.lpstrFile, filePos)
        Debug.Print "The user Chose " & Trim(fileName)
        FileOpen = True
    End If
    Exit Function
    
err_FileOpen:
    ReportError MODULE_NAME, "modCommonDialog"
End Function
' ---------------------------------------------------------------------

Attribute VB_Name = "modMDL"
Option Explicit
' ---------------------------------------------------------------------
Private Const MODULE_NAME                   As String = "modMDL"
' ---------------------------------------------------------------------
'   MDL function declarations
' ---------------------------------------------------------------------
Declare Function mdlElmdscr_pointAtDistance Lib "stdmdlbltin.dll" ( _
        ByRef position As Point3d, _
        ByRef tangent As Point3d, _
        ByVal inputDistance As Double, _
        ByVal edP As Long, _
        ByVal inputTolerance As Double) As Long
        
Private Const SUCCESS                       As Long = 0
' ---------------------------------------------------------------------
Public Function PointAtDistanceAlongElement( _
        ByRef position As Point3d, _
        ByRef tangent As Point3d, _
        ByVal distance As Double, _
        ByVal oElement As Element) As Boolean
    Dim res                                 As Long
    Const Tolerance                         As Double = 0.0001
    'Dim tangent2                            As Point3d
    res = mdlElmdscr_pointAtDistance(position, tangent, distance, oElement.MdlElementDescrP, Tolerance)
    'Dim tangentOrigin                       As Point3d
    'tangentOrigin = Point3dAdd(position, tangent2)
    PointAtDistanceAlongElement = (SUCCESS = res)
End Function
' ---------------------------------------------------------------------

Attribute VB_Name = "modMain"
Option Explicit
' ---------------------------------------------------------------------
Private Const MODULE_NAME                   As String = "modMain"
Private Const VERSION_                      As String = "16.5.31.1"
' ---------------------------------------------------------------------
'   Notice:
'   This code is provided to illustrate MicroStation VBA programming.
'   It is not guaranteed fit for any particular purpose.  Use at your
'   own risk.
'   LA Solutions provides this software to show how to place points
'   along a line or line-string element.  The code is supplied as-is
'   for demonstration and is not production software.
'   You may use this software for any purpose commercial or private
'   provided that this notice is retained in full.
'   www.la-solutions.co.uk
'   End of Notice
' ---------------------------------------------------------------------
'   References:
'   This project references the Windows Scripting Runtime DLL
' ---------------------------------------------------------------------
'   Main entry point.  Key-in:
'   vba run [PlacePointsAlongLine]modMain.Main
' ---------------------------------------------------------------------
Public Sub Main()
    On Error GoTo err_Main
    
    Dim msg                                 As String
    msg = "[PlacePointsAlongLine]modMain.Main version " & Version()
    Debug.Print msg
    ShowMessage msg, msg, msdMessageCenterPriorityInfo, False
    frmPlacePointsAlongLine.Show vbModeless
    Exit Sub
    
err_Main:
    ReportError MODULE_NAME, "Main"
End Sub
' ---------------------------------------------------------------------
'   ParseDistanceFile
'   Parse a text file containing distance data into an array of Double
'   We're expecting a simple list of values, each value on a new line.
'   Not much CSV involved!
'   Return: Long count of points parsed from file
' ---------------------------------------------------------------------
Public Function ParseDistanceFile(ByRef data() As Double, ByVal fileName As String) As Long
    ParseDistanceFile = 0
    On Error GoTo err_ParseDistanceFile
    ReDim data(0) As Double
    Dim count                               As Long
    count = 0
    Dim oFileSystem                         As New Scripting.FileSystemObject
    Dim reader                              As Scripting.TextStream
    Set reader = oFileSystem.OpenTextFile(fileName, ForReading)
    Debug.Print "Opened '" & fileName & "' for reading"
    Dim line                                As String
    Do Until reader.AtEndOfStream
        line = reader.ReadLine
        If IsNumeric(line) Then
            Dim distance                    As Double
            distance = CDbl(line)
            If 0# < distance Then
                '   Only positive values are useful
                ReDim Preserve data(0 To count) As Double
                data(count) = distance
                count = 1 + count
                Debug.Print "Distance [" & CStr(count) & "]=" & Format(distance, "0.00")
            End If
        End If
    Loop
    reader.Close
    Set oFileSystem = Nothing
    ParseDistanceFile = count
    Exit Function
    
err_ParseDistanceFile:
    ReportError MODULE_NAME, "ParseDistanceFile"
End Function
' ---------------------------------------------------------------------
'   ReverseElement
'   Only certain types of Element may be reversed
' ---------------------------------------------------------------------
Public Function ReverseElement(ByVal oElement As Element) As Boolean
    ReverseElement = True
    Select Case oElement.Type
        Case msdElementTypeLine, msdElementTypeLineString
            oElement.AsLineElement.Reverse
        Case msdElementTypeComplexString
            oElement.AsComplexStringElement.Reverse
        Case msdElementTypeArc
            oElement.AsArcElement.Reverse
        Case msdElementTypeBsplineCurve
            oElement.AsBsplineCurveElement.Reverse
        Case Else
            ReverseElement = False
            Dim msg                         As String
            msg = "Can't reverse element type " & CStr(oElement.Type)
            ShowMessage msg, msg, msdMessageCenterPriorityWarning, True
    End Select
End Function
' ---------------------------------------------------------------------
'   ElementSupportsPointAtDistance
'   Return: True if this element supports the Element.PointAtDistance
'   method.
' ---------------------------------------------------------------------
Public Function ElementSupportsPointAtDistance(ByVal oElement As Element) As Boolean
    Select Case oElement.Type
    Case msdElementTypeLine, msdElementTypeLineString
        ElementSupportsPointAtDistance = True
    Case msdElementTypeComplexString
        ElementSupportsPointAtDistance = True
    Case msdElementTypeArc
        ElementSupportsPointAtDistance = True
    Case msdElementTypeBsplineCurve
        ElementSupportsPointAtDistance = True
    Case Else
        ElementSupportsPointAtDistance = False
    End Select
End Function
' ---------------------------------------------------------------------
'   MarkElementStart
' ---------------------------------------------------------------------
Public Sub MarkElementStart(ByVal oElement As Element, ByVal radius As Double, ByVal oTransients As TransientElementContainer)
    Dim valid                               As Boolean
    valid = True
    Dim startPoint                          As Point3d
    Select Case oElement.Type
    Case msdElementTypeLine, msdElementTypeLineString
        startPoint = oElement.AsLineElement.startPoint
    Case msdElementTypeComplexString
        startPoint = oElement.AsComplexStringElement.startPoint
    Case msdElementTypeArc
        startPoint = oElement.AsArcElement.startPoint
    Case msdElementTypeBsplineCurve
        startPoint = oElement.AsBsplineCurveElement.startPoint
    Case Else
        valid = False
    End Select
    If valid Then
        oTransients.Reset
        MarkPoint startPoint, radius, oTransients
    End If
End Sub
' ---------------------------------------------------------------------
'   MarkPoint
'   Draw a transient marker at a point of size 'radius'
' ---------------------------------------------------------------------
Public Sub MarkPoint(ByRef origin As Point3d, ByVal radius As Double, ByVal oTransients As TransientElementContainer)
    On Error GoTo err_MarkPoint
    Debug.Assert Not oTransients Is Nothing
    Dim oCircle                             As EllipseElement
    Set oCircle = CreateEllipseElement2(Nothing, origin, radius, radius, Matrix3dIdentity, msdFillModeUseActive)
    oTransients.AppendCopyOfElement oCircle
    Exit Sub
    
err_MarkPoint:
    ReportError MODULE_NAME, "MarkPoint"
End Sub
' ---------------------------------------------------------------------
Public Function Version() As String
    Version = VERSION_
End Function
' ---------------------------------------------------------------------
Public Function ArraySize(arr As Variant) As Long
    ArraySize = 0
    If Not IsArray(arr) Then Exit Function
    ArraySize = UBound(arr) - LBound(arr) + 1
End Function
' ---------------------------------------------------------------------
'   ReportError
'   Report errors in a consistent manner
' ---------------------------------------------------------------------
Public Sub ReportError(ByVal moduleName As String, ByVal procName As String)
    MsgBox "Error no. " & CStr(Err.Number) & ": " & Err.Description & vbNewLine & "Caused by " & Err.Source, vbOKOnly Or vbExclamation, "Error in " & moduleName & ":" & procName
End Sub
' ---------------------------------------------------------------------
