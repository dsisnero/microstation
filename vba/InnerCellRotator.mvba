Attribute VB_Name = "clsCellLocator"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
' ---------------------------------------------------------------------
Private Const MODULE_NAME                   As String = "clsCellLocator"
' ---------------------------------------------------------------------
Implements ILocateCommandEvents
' ---------------------------------------------------------------------
Private m_InnerCell                         As clsCellLocator
Private m_oCellManager                      As clsCellManager
Private m_strInnerCellName                  As String
Private m_oParent                           As frmCellManager
' ---------------------------------------------------------------------
Public Property Set CellManager(ByVal oManager As clsCellManager)
    Set m_oCellManager = oManager
End Property
' ---------------------------------------------------------------------
Public Property Set Parent(ByVal oFrm As UserForm)
    Set m_oParent = oFrm
End Property
' ---------------------------------------------------------------------
Public Property Let InnerCellName(ByVal name As String)
    m_strInnerCellName = name
End Property
' ---------------------------------------------------------------------
Private Sub Class_Initialize()
End Sub
' ---------------------------------------------------------------------
Private Sub ILocateCommandEvents_Accept(ByVal oElement As Element, Point As Point3d, ByVal View As View)
    Dim msg                                 As String
    msg = "Accept element type " & oElement.Type
    ShowMessage msg, msg, msdMessageCenterPriorityDebug, False
    Debug.Print msg
    If oElement.IsCellElement Then
        msg = "Accept cell " & Quote(oElement.AsCellElement.name)
        m_oParent.CellName = oElement.AsCellElement.name
        ShowMessage msg, msg, msdMessageCenterPriorityDebug, False
        Debug.Print msg
        Set m_oCellManager.OuterCell = oElement.AsCellElement
        If m_oCellManager.HasInnerCell(m_strInnerCellName) Then
            msg = "Found inner cell " & Quote(m_oCellManager.InnerCellName)
            m_oParent.InnerCellName = m_oCellManager.InnerCellName
            ShowMessage msg, msg, msdMessageCenterPriorityDebug, False
            Debug.Print msg
        End If
    End If
End Sub
' ---------------------------------------------------------------------
Private Sub ILocateCommandEvents_Cleanup()

End Sub
' ---------------------------------------------------------------------
Private Sub ILocateCommandEvents_Dynamics(Point As Point3d, ByVal View As View, ByVal DrawMode As MsdDrawingMode)

End Sub
' ---------------------------------------------------------------------
Private Sub ILocateCommandEvents_LocateFailed()

End Sub
' ---------------------------------------------------------------------
Private Sub ILocateCommandEvents_LocateFilter(ByVal oElement As Element, Point As Point3d, accepted As Boolean)
    accepted = oElement.IsCellElement
End Sub
' ---------------------------------------------------------------------
Private Sub ILocateCommandEvents_LocateReset()

End Sub
' ---------------------------------------------------------------------
Private Sub ILocateCommandEvents_Start()
    If m_oCellManager Is Nothing Then
        Dim warn                            As String
        warn = MODULE_NAME & ": m_oCellManager is NULL"
        ShowMessage warn, warn, msdMessageCenterPriorityError, True
        Exit Sub
    End If
    
    Dim oLocateCriteria                     As LocateCriteria
    '  Set the locate criteria to disallow  read-only elements.
    Const WillModifyElements                As Boolean = True
    Set oLocateCriteria = CommandState.CreateLocateCriteria(WillModifyElements)
    CommandState.SetLocateCriteria oLocateCriteria

    ShowCommand "Rotate Inner Cell"
    ShowPrompt "Select a cell"
End Sub
' ---------------------------------------------------------------------

Attribute VB_Name = "clsCellManager"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
' ---------------------------------------------------------------------
Private Const MODULE_NAME                   As String = "clsCellManager"
' ---------------------------------------------------------------------
'   Class Cell Manager provides ways to analyse a cell, rotate an inner
'   cell.
' ---------------------------------------------------------------------
Private m_oInnerCell                        As CellElement
Private m_oOuterCell                        As CellElement
Private m_oParent                           As frmCellManager
' ---------------------------------------------------------------------
Public Property Set Parent(ByVal oFrm As UserForm)
    Set m_oParent = oFrm
End Property
' ---------------------------------------------------------------------
Public Property Set OuterCell(ByVal oCell As CellElement)
    Set m_oOuterCell = oCell
End Property
' ---------------------------------------------------------------------
Public Property Get InnerCellName() As String
    If m_oInnerCell Is Nothing Then
        InnerCellName = vbNullString
    Else
        InnerCellName = m_oInnerCell.name
        m_oParent.InnerCellName = m_oInnerCell.name
    End If
End Property
' ---------------------------------------------------------------------
Public Function HasInnerCell(ByVal InnerCellName As String) As Boolean
    HasInnerCell = False
    On Error GoTo err_HasInnerCell
    Dim oComponents                         As ElementEnumerator
    Set oComponents = m_oOuterCell.GetSubElements
    Do While oComponents.MoveNext
        If oComponents.Current.IsCellElement Then
            Dim oInner                      As CellElement
            Set oInner = oComponents.Current.AsCellElement
            If 0 = StrComp(InnerCellName, oInner.name, vbTextCompare) Then
                Set m_oInnerCell = oInner
                HasInnerCell = True
                Exit Function
            End If
        End If
    Loop
    Exit Function
    
err_HasInnerCell:
    ReportError MODULE_NAME, "HasInnerCell"
End Function
' ---------------------------------------------------------------------
'   IsInnerCell
'   Test a cell component to determine whether it is a cell and, if so,
'   if its name matches our requirement
' ---------------------------------------------------------------------
Public Function IsInnerCell(ByVal oElement As Element) As Boolean
    IsInnerCell = False
    If oElement.IsCellElement Then
        Dim oCell                           As CellElement
        Set oCell = oElement.AsCellElement
        If 0 = StrComp(oCell.name, m_oInnerCell.name) Then
            IsInnerCell = True
        End If
    End If
End Function
' ---------------------------------------------------------------------
'   RotateInnerCell
'   Rotate the inner annotation cell by specified angle and rewrite the
'   outer cell.
' ---------------------------------------------------------------------
Public Function RotateInnerCell(ByVal degrees As Double) As Boolean
    RotateInnerCell = False
    On Error GoTo err_RotateInnerCell
    Dim oSubElement                         As Element
    Dim oInnerCell                          As CellElement
    Do While m_oOuterCell.MoveToNextElement
        Set oSubElement = m_oOuterCell.CopyCurrentElement
        If IsInnerCell(oSubElement) Then
            Set oInnerCell = oSubElement.AsCellElement
            oInnerCell.Rotate oInnerCell.Origin, 0#, 0#, radians(degrees)
            m_oOuterCell.ReplaceCurrentElement oInnerCell
            m_oOuterCell.Rewrite
            RotateInnerCell = True
        End If
    Loop
    Exit Function
    
err_RotateInnerCell:
    ReportError MODULE_NAME, "RotateInnerCell"
End Function

Attribute VB_Name = "frmCellManager"
Attribute VB_Base = "0{EDDAB389-E4E2-4DB2-95EC-F34A10856506}{82BAFB60-C552-4741-8987-BF9E2123C745}"
Attribute VB_GlobalNameSpace = False
Attribute VB_Creatable = False
Attribute VB_PredeclaredId = True
Attribute VB_Exposed = False
Attribute VB_TemplateDerived = False
Attribute VB_Customizable = False
Option Explicit
' ---------------------------------------------------------------------
Private Const MODULE_NAME                   As String = "frmCellManager"
' ---------------------------------------------------------------------
Private m_dblRotationDegrees                As Double
Private m_strInnerCellName                  As String
Private m_oCellManager                      As clsCellManager
' ---------------------------------------------------------------------
Public Property Get CellManager() As clsCellManager
    Set CellManager = m_oCellManager
End Property
' ---------------------------------------------------------------------
Public Property Let CellName(ByVal name As String)
    txtCellName.Text = name
End Property
Public Property Get CellName() As String
    CellName = txtCellName.Text
End Property
' ---------------------------------------------------------------------
Public Property Let InnerCellName(ByVal name As String)
    m_strInnerCellName = name
    txtInnerCellName.Text = m_strInnerCellName
End Property
Public Property Get InnerCellName() As String
    InnerCellName = m_strInnerCellName
End Property
' ---------------------------------------------------------------------
Public Property Let Rotation(ByVal degrees As Double)
    m_dblRotationDegrees = degrees
    txtRotateBy.Text = Format(m_dblRotationDegrees, "##0.00")
End Property
Public Property Get Rotation() As Double
    Rotation = m_dblRotationDegrees
End Property
' ---------------------------------------------------------------------
Private Sub cmdPickCell_Click()
    Dim oLocator                            As New clsCellLocator
    Set oLocator.Parent = Me
    Set oLocator.CellManager = m_oCellManager
    oLocator.InnerCellName = m_strInnerCellName
    CommandState.StartLocate oLocator
End Sub
' ---------------------------------------------------------------------
Private Sub cmdRotate_Click()
    Dim msg                                 As String
    msg = "cmdRotate_Click"
    ShowMessage msg, msg, msdMessageCenterPriorityInfo, False
    Debug.Print msg
    If m_oCellManager Is Nothing Then
        msg = "You forget to initialise m_oCellManager"
        ShowMessage msg, msg, msdMessageCenterPriorityError, True
    Else
        If m_oCellManager.RotateInnerCell(CDbl(txtRotateBy.Text)) Then
        Else
        End If
    End If
End Sub
' ---------------------------------------------------------------------
Private Sub UserForm_Initialize()
    m_strInnerCellName = "Annotation-1"
    txtInnerCellName.Text = m_strInnerCellName
    txtRotateBy.Text = Format(0#, "##0.00")
    Set m_oCellManager = New clsCellManager
End Sub
' ---------------------------------------------------------------------

Attribute VB_Name = "modMain"
Option Explicit
' ---------------------------------------------------------------------
Private Const MODULE_NAME                   As String = "modMain"
Private Const Version_                      As String = "19.01.08"
' ---------------------------------------------------------------------
'   Notice:
'   This MicroStation VBA macro is designed to rotate a cell nested inside
'   another cell.  The motive for this is annotation inside a cell.  If the
'   outer cell is rotated, we want to counter-rotate the inner cell to keep
'   it aligned with the view or coordinate system.
'
'   This code is written to demonstrate MicroStation VBA coding.  It is
'   not fit for any particular purpose.  Use at your own risk.
'
'   You may use this code for any purpose provided that this notice is
'   retained in full.
'
'   Visit our website:
'   http://www.la-solutions.co.uk
'
'   End of notice
' ---------------------------------------------------------------------
'   History
'   03-Oct-18   First release
'   28-Sep-18   Project start
' ---------------------------------------------------------------------
'   Main
'   Main entry point
'   key-in:
'   vba run [InnerCellRotator]modMain.Main
' ---------------------------------------------------------------------
Public Sub Main()
    On Error GoTo err_Main
    Dim msg                                 As String
    msg = "InnterCellRotator version " & Version()
    ShowMessage msg, msg, msdMessageCenterPriorityInfo, False
    Dim oFrm                                As New frmCellManager
    oFrm.InnerCellName = "Annotation-1"
    oFrm.Show vbModeless
    Exit Sub
    
err_Main:
    ReportError MODULE_NAME, "Main"
End Sub
' ---------------------------------------------------------------------
Public Function Version() As String
    Version = Version_
End Function
' ---------------------------------------------------------------------
'   DoubleQuote
'   Wrap string in double quotes
' ---------------------------------------------------------------------
Public Function DoubleQuote(ByVal s As String) As String
    Const Quote                             As String = """"
    DoubleQuote = Quote & s & Quote
End Function
' ---------------------------------------------------------------------
'   Quote
'   Wrap string in single quotes
' ---------------------------------------------------------------------
Public Function Quote(ByVal s As String) As String
    Const SingleQuote                       As String = "'"
    Quote = SingleQuote & s & SingleQuote
End Function
' ---------------------------------------------------------------------
'   FormatDouble
'   Create a String with a formatted double number
' ---------------------------------------------------------------------
Function FormatDouble(ByVal val As Double) As String
    FormatDouble = Format(val, "##0.00")
End Function
' ---------------------------------------------------------------------
'   FormatPoint3dXY
'   Format the XY components of a Point3d into a string
' ---------------------------------------------------------------------
Function FormatPoint3dXY(ByRef p As Point3d) As String
    FormatPoint3dXY = FormatDouble(p.X) & "," & FormatDouble(p.Y)
End Function
' ---------------------------------------------------------------------
'   ReportError
'   Provides consistent error reporting
' ---------------------------------------------------------------------
Public Sub ReportError(ByVal moduleName As String, ByVal procName As String)
    MsgBox "Error " & CStr(Err.Number) & " was caused by " & vbNewLine & _
        Err.Source & ". " & vbNewLine & _
        Err.Description, vbOKOnly Or vbExclamation, "Error in " & moduleName & ":" & procName
End Sub
' ---------------------------------------------------------------------
