Attribute VB_Name = "clsElementMover"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
' ---------------------------------------------------------------------
Private Const sMODULE_NAME          As String = "clsElementMover"
' ---------------------------------------------------------------------
'   Notice:
'
'   ElementMover is provided by LA Solutions at no cost and with
'   no license requirement as part of the MoveElement example project
'
'   This software is provided with no warranty and no declaration of
'   fitness for any purpose.  No support is provided.
'   You may use this software and copy it to others inside or outside
'   your organisation provided that this notice is retained in full.
'
'   Copyright © 2005 LA Solutions Ltd
' ---------------------------------------------------------------------
'   class ElementMover provides a container mechanism for MoveElement's Locator
'   and Move classes
'
' ---------------------------------------------------------------------
Private m_oElement                  As Element '  The element to be moved
Private m_ptOrigin                  As Point3d
Private m_ptTarget                  As Point3d
' ---------------------------------------------------------------------
Public Property Get ElementToMove() As Element
    Set ElementToMove = m_oElement
End Property
Public Property Set ElementToMove(e As Element)
    Set m_oElement = e
    If (e.IsTextElement) Then
        With e.AsTextElement
            Debug.Print "Move text '" & .Text & "'"
        End With
    End If
End Property
' ---------------------------------------------------------------------
Public Property Get Origin() As Point3d
    Origin = m_ptOrigin
End Property
Public Property Let Origin(o As Point3d)
     m_ptOrigin = o
    Debug.Print "Origin XY=" & Format(o.X, "#,##0.0") & "," & Format(o.Y, "#,##0.0")
End Property
' ---------------------------------------------------------------------
Public Property Get Target() As Point3d
    Target = m_ptTarget
End Property
Public Property Let Target(o As Point3d)
     m_ptTarget = o
    Debug.Print "Target XY=" & Format(o.X, "#,##0.0") & "," & Format(o.Y, "#,##0.0")
End Property
' ---------------------------------------------------------------------
Public Sub LocateElement()
    On Error GoTo err_LocateElement
    
    Init
    
    Dim oLocator    As New clsLocator
    Set oLocator.ElementMover = Me
    CommandState.StartLocate oLocator
    Exit Sub
    
err_LocateElement:
    ReportError sMODULE_NAME, "LocateElement"
End Sub
' ---------------------------------------------------------------------
Private Sub Init()
    Set m_oElement = Nothing
    m_ptOrigin = Point3dZero
    m_ptTarget = Point3dZero
End Sub
' ---------------------------------------------------------------------

Private Sub Class_Initialize()
    Init
End Sub

Attribute VB_Name = "clsGetTarget"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
' ---------------------------------------------------------------------
'   Notice:
'
'   GetTarget is provided by LA Solutions at no cost and with
'   no license requirement as part of the MoveElement example project
'
'   This software is provided with no warranty and no declaration of
'   fitness for any purpose.  No support is provided.
'   You may use this software and copy it to others inside or outside
'   your organisation provided that this notice is retained in full.
'
'   Copyright © 2005 LA Solutions Ltd
' ---------------------------------------------------------------------
Private Const sMODULE_NAME          As String = "clsGetTarget"
' ---------------------------------------------------------------------
Private m_oElementMover             As clsElementMover
Private m_oElement                  As Element  '   The located element
Private m_oClone                    As Element  '   Used in dynamics to show new location
Private m_oOrigin                   As Point3d
' ---------------------------------------------------------------------
Implements IPrimitiveCommandEvents
' ---------------------------------------------------------------------
Public Property Set ElementMover(o As clsElementMover)
    Set m_oElementMover = o
    Set m_oElement = m_oElementMover.ElementToMove
    m_oOrigin = m_oElementMover.Origin
End Property
' ---------------------------------------------------------------------
Private Sub IPrimitiveCommandEvents_Cleanup()
    Set m_oElement = Nothing
    Set m_oElementMover = Nothing
End Sub
' ---------------------------------------------------------------------
Private Sub IPrimitiveCommandEvents_DataPoint(oPoint As Point3d, ByVal oView As View)
    m_oElementMover.Target = oPoint
    If (MoveElement(m_oElement, oPoint, msdDrawingModeNormal)) Then
        m_oElement.Rewrite
    End If
    m_oElementMover.LocateElement
End Sub
' ---------------------------------------------------------------------
Private Sub IPrimitiveCommandEvents_Dynamics(oPoint As Point3d, ByVal oView As View, ByVal drawMode As MsdDrawingMode)
    Dim oClone          As Element
    Set oClone = m_oElement.Clone
    MoveElement oClone, oPoint, drawMode
End Sub
' ---------------------------------------------------------------------
Private Sub IPrimitiveCommandEvents_Keyin(ByVal Keyin As String)

End Sub
' ---------------------------------------------------------------------
Private Sub IPrimitiveCommandEvents_Reset()

End Sub
' ---------------------------------------------------------------------
Private Sub IPrimitiveCommandEvents_Start()
    CommandState.StartDynamics
    ShowCommand "Datapoint New Location"
    ShowPrompt "Datapoint new origin of element"
End Sub
' ---------------------------------------------------------------------
Private Function MoveElement(oElement As Element, oPoint As Point3d, ByVal drawMode As MsdDrawingMode) As Boolean
    MoveElement = False
    On Error GoTo err_MoveElement
    
    oElement.Redraw msdDrawingModeTemporaryErase
   
    '   Make a transform
    Dim offset          As Point3d
    offset = Point3dSubtract(oPoint, m_oOrigin)
    
    '   Apply the transform to our element
    oElement.Move offset
    oElement.Redraw drawMode
    MoveElement = True
    Exit Function
    
err_MoveElement:
    ReportError sMODULE_NAME, "MoveElement"
End Function
' ---------------------------------------------------------------------

Attribute VB_Name = "clsLocator"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
Option Explicit
' ---------------------------------------------------------------------
'   Notice:
'
'   Locator is provided by LA Solutions at no cost and with
'   no license requirement as part of the MoveElement example project
'
'   This software is provided with no warranty and no declaration of
'   fitness for any purpose.  No support is provided.
'   You may use this software and copy it to others inside or outside
'   your organisation provided that this notice is retained in full.
'
'   Copyright © 2005 LA Solutions Ltd
' ---------------------------------------------------------------------
Private Const sMODULE_NAME          As String = "clsLocator"
' ---------------------------------------------------------------------
Private m_oElementMover             As clsElementMover
' ---------------------------------------------------------------------
Implements ILocateCommandEvents

' ---------------------------------------------------------------------
Public Property Set ElementMover(o As clsElementMover)
    Set m_oElementMover = o
End Property
' ---------------------------------------------------------------------
Private Sub ILocateCommandEvents_Accept(ByVal oElement As Element, oPoint As Point3d, ByVal View As View)
    Set m_oElementMover.ElementToMove = oElement
    m_oElementMover.Origin = oPoint
    Dim oGetTarget    As New clsGetTarget
    Set oGetTarget.ElementMover = m_oElementMover
    CommandState.StartPrimitive oGetTarget
End Sub
' ---------------------------------------------------------------------
Private Sub ILocateCommandEvents_Cleanup()
    Set m_oElementMover = Nothing
End Sub
' ---------------------------------------------------------------------
Private Sub ILocateCommandEvents_Dynamics(oPoint As Point3d, ByVal oView As View, ByVal drawMode As MsdDrawingMode)

End Sub
' ---------------------------------------------------------------------
Private Sub ILocateCommandEvents_LocateFailed()

End Sub
' ---------------------------------------------------------------------
'   In this example, we're restricting the acceptable elements to
'   just TextElements
' ---------------------------------------------------------------------
Private Sub ILocateCommandEvents_LocateFilter(ByVal oElement As Element, oPoint As Point3d, accepted As Boolean)
    accepted = False
    If (oElement.IsTextElement) Then accepted = True
End Sub
' ---------------------------------------------------------------------
Private Sub ILocateCommandEvents_LocateReset()

End Sub
' ---------------------------------------------------------------------
Private Sub ILocateCommandEvents_Start()
    Dim oLocateCriteria As LocateCriteria
    '  Since this command does modify the original element,
    '  set the locate criteria to allow writable elements.
    Set oLocateCriteria = CommandState.CreateLocateCriteria(True)
    CommandState.SetLocateCriteria oLocateCriteria
    
    '  MicroStation disables AccuSnap whenever a new command starts, so a command
    '  should enable AccuSnap whenever it is appropriate.  This user still has the
    '  ability to turn off AccuSnap. Enabling AccuSnap does not override that.
    '  EnableAccuSnap only enables AccuSnap if the user has it turned on.
    CommandState.EnableAccuSnap
    
    ShowCommand "Move Text Element"
    ShowPrompt "Select text element to move"
End Sub
' ---------------------------------------------------------------------

Attribute VB_Name = "modMain"
Option Explicit
' ---------------------------------------------------------------------
Private Const sMODULE_NAME          As String = "modMain"
Private Const nDateStamp            As Long = 20050416 ' Year/month/day
' ---------------------------------------------------------------------
'   Description:
'
'   Example code shows how to locate an element and move to a location
'   supplied by a user
'
' ---------------------------------------------------------------------
'   To run this utility keyin:
'   vba run [MoveElement]modMain.Main
' ---------------------------------------------------------------------
'   Notice:
'
'   MoveElement is provided by LA Solutions at no cost and
'   with no license requirement
'
'   This software is provided with no warranty and no declaration of
'   fitness for any purpose.  No support is provided.
'   You may use this software and copy it to others inside or outside
'   your organisation provided that this notice is retained in full.
'
'   Copyright © 2005 LA Solutions Ltd
' ---------------------------------------------------------------------
Sub Main()
    On Error GoTo err_Main
    Dim oElementMover As New clsElementMover
    oElementMover.LocateElement
    Exit Sub
    
err_Main:
    ReportError sMODULE_NAME, "Main"
End Sub
' ---------------------------------------------------------------------
'   ReportError
' ---------------------------------------------------------------------
Sub ReportError(moduleName As String, procName As String)
    Dim msg         As String
    msg = "TextFileWriter error no. " & CStr(Err.Number) & ": " & Err.Description
    ShowMessage msg, msg & "Occurred in procedure '" & procName & "'", msdMessageCenterPriorityError, True
End Sub
' ---------------------------------------------------------------------
